-- Generated from userdefs.asn.mako for package control_msgs

UserDefs-Control-msgs-Types DEFINITIONS ::=
BEGIN

IMPORTS T-UInt32 FROM TASTE-BasicTypes;

    -- Dummy type (TASTE doesn't handle the includes correctly if an ASN.1 file defines only constants)
    Dummy-Control-msgs-Types-T ::= T-UInt32

    -- Size constants definitions: to be set according to the application's needs

    -- Size constant for type Control-msgs-JointTrajectoryControllerState
    max-Control-msgs-JointTrajectoryControllerState T-UInt32 ::= 60

    -- Size constant for type Control-msgs-FollowJointTrajectoryFeedback
    max-Control-msgs-FollowJointTrajectoryFeedback T-UInt32 ::= 60

    -- Size constant for type Control-msgs-FollowJointTrajectoryGoal
    max-Control-msgs-FollowJointTrajectoryGoal T-UInt32 ::= 60

END
