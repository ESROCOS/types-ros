-- Generated from package.asn.mako for package actionlib_tutorials

Actionlib-tutorials-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Actionlib-msgs-GoalID, Actionlib-msgs-GoalStatus FROM Actionlib-msgs-Types
Std-msgs-Header FROM Std-msgs-Types
max-Actionlib-tutorials-FibonacciFeedback, max-Actionlib-tutorials-FibonacciResult, Dummy-Actionlib-tutorials-Types-T FROM UserDefs-Actionlib-tutorials-Types;
    -- ================================================================================
    -- Message Actionlib-tutorials-Types/AveragingAction
    -- ================================================================================
    -- # ====== DO NOT MODIFY! AUTOGENERATED FROM AN ACTION DEFINITION ======
    -- 
    -- AveragingActionGoal action_goal
    -- AveragingActionResult action_result
    -- AveragingActionFeedback action_feedback
    -- 
    -- ================================================================================
    -- MSG: actionlib_tutorials/AveragingActionGoal
    -- # ====== DO NOT MODIFY! AUTOGENERATED FROM AN ACTION DEFINITION ======
    -- 
    -- Header header
    -- actionlib_msgs/GoalID goal_id
    -- AveragingGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/AveragingGoal
    -- # ====== DO NOT MODIFY! AUTOGENERATED FROM AN ACTION DEFINITION ======
    -- #goal definition
    -- int32 samples
    -- 
    -- ================================================================================
    -- MSG: actionlib_tutorials/AveragingActionResult
    -- # ====== DO NOT MODIFY! AUTOGENERATED FROM AN ACTION DEFINITION ======
    -- 
    -- Header header
    -- actionlib_msgs/GoalStatus status
    -- AveragingResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_tutorials/AveragingResult
    -- # ====== DO NOT MODIFY! AUTOGENERATED FROM AN ACTION DEFINITION ======
    -- #result definition
    -- float32 mean
    -- float32 std_dev
    -- 
    -- ================================================================================
    -- MSG: actionlib_tutorials/AveragingActionFeedback
    -- # ====== DO NOT MODIFY! AUTOGENERATED FROM AN ACTION DEFINITION ======
    -- 
    -- Header header
    -- actionlib_msgs/GoalStatus status
    -- AveragingFeedback feedback
    -- 
    -- ================================================================================
    -- MSG: actionlib_tutorials/AveragingFeedback
    -- # ====== DO NOT MODIFY! AUTOGENERATED FROM AN ACTION DEFINITION ======
    -- #feedback
    -- int32 sample
    -- float32 data
    -- float32 mean
    -- float32 std_dev
    -- 
    -- ================================================================================
    -- ASN.1 type for Actionlib-tutorials-Types/AveragingAction
    Actionlib-tutorials-AveragingAction ::= SEQUENCE
    {
        action-goal Actionlib-tutorials-AveragingActionGoal,
        action-result Actionlib-tutorials-AveragingActionResult,
        action-feedback Actionlib-tutorials-AveragingActionFeedback
    }
    -- ================================================================================

    -- ================================================================================
    -- Message Actionlib-tutorials-Types/AveragingActionFeedback
    -- ================================================================================
    -- # ====== DO NOT MODIFY! AUTOGENERATED FROM AN ACTION DEFINITION ======
    -- 
    -- Header header
    -- actionlib_msgs/GoalStatus status
    -- AveragingFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/AveragingFeedback
    -- # ====== DO NOT MODIFY! AUTOGENERATED FROM AN ACTION DEFINITION ======
    -- #feedback
    -- int32 sample
    -- float32 data
    -- float32 mean
    -- float32 std_dev
    -- 
    -- ================================================================================
    -- ASN.1 type for Actionlib-tutorials-Types/AveragingActionFeedback
    Actionlib-tutorials-AveragingActionFeedback ::= SEQUENCE
    {
        header Std-msgs-Header,
        status Actionlib-msgs-GoalStatus,
        feedback Actionlib-tutorials-AveragingFeedback
    }
    -- ================================================================================

    -- ================================================================================
    -- Message Actionlib-tutorials-Types/AveragingActionGoal
    -- ================================================================================
    -- # ====== DO NOT MODIFY! AUTOGENERATED FROM AN ACTION DEFINITION ======
    -- 
    -- Header header
    -- actionlib_msgs/GoalID goal_id
    -- AveragingGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/AveragingGoal
    -- # ====== DO NOT MODIFY! AUTOGENERATED FROM AN ACTION DEFINITION ======
    -- #goal definition
    -- int32 samples
    -- ================================================================================
    -- ASN.1 type for Actionlib-tutorials-Types/AveragingActionGoal
    Actionlib-tutorials-AveragingActionGoal ::= SEQUENCE
    {
        header Std-msgs-Header,
        goal-id Actionlib-msgs-GoalID,
        goal Actionlib-tutorials-AveragingGoal
    }
    -- ================================================================================

    -- ================================================================================
    -- Message Actionlib-tutorials-Types/AveragingActionResult
    -- ================================================================================
    -- # ====== DO NOT MODIFY! AUTOGENERATED FROM AN ACTION DEFINITION ======
    -- 
    -- Header header
    -- actionlib_msgs/GoalStatus status
    -- AveragingResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/AveragingResult
    -- # ====== DO NOT MODIFY! AUTOGENERATED FROM AN ACTION DEFINITION ======
    -- #result definition
    -- float32 mean
    -- float32 std_dev
    -- ================================================================================
    -- ASN.1 type for Actionlib-tutorials-Types/AveragingActionResult
    Actionlib-tutorials-AveragingActionResult ::= SEQUENCE
    {
        header Std-msgs-Header,
        status Actionlib-msgs-GoalStatus,
        result Actionlib-tutorials-AveragingResult
    }
    -- ================================================================================

    -- ================================================================================
    -- Message Actionlib-tutorials-Types/AveragingFeedback
    -- ================================================================================
    -- # ====== DO NOT MODIFY! AUTOGENERATED FROM AN ACTION DEFINITION ======
    -- #feedback
    -- int32 sample
    -- float32 data
    -- float32 mean
    -- float32 std_dev
    -- 
    -- ================================================================================
    -- ASN.1 type for Actionlib-tutorials-Types/AveragingFeedback
    Actionlib-tutorials-AveragingFeedback ::= SEQUENCE
    {
        sample T-Int32,
        data-value T-Float,
        mean T-Float,
        std-dev T-Float
    }
    -- ================================================================================

    -- ================================================================================
    -- Message Actionlib-tutorials-Types/AveragingGoal
    -- ================================================================================
    -- # ====== DO NOT MODIFY! AUTOGENERATED FROM AN ACTION DEFINITION ======
    -- #goal definition
    -- int32 samples
    -- ================================================================================
    -- ASN.1 type for Actionlib-tutorials-Types/AveragingGoal
    Actionlib-tutorials-AveragingGoal ::= T-Int32

    -- ================================================================================

    -- ================================================================================
    -- Message Actionlib-tutorials-Types/AveragingResult
    -- ================================================================================
    -- # ====== DO NOT MODIFY! AUTOGENERATED FROM AN ACTION DEFINITION ======
    -- #result definition
    -- float32 mean
    -- float32 std_dev
    -- ================================================================================
    -- ASN.1 type for Actionlib-tutorials-Types/AveragingResult
    Actionlib-tutorials-AveragingResult ::= SEQUENCE
    {
        mean T-Float,
        std-dev T-Float
    }
    -- ================================================================================

    -- ================================================================================
    -- Message Actionlib-tutorials-Types/FibonacciAction
    -- ================================================================================
    -- # ====== DO NOT MODIFY! AUTOGENERATED FROM AN ACTION DEFINITION ======
    -- 
    -- FibonacciActionGoal action_goal
    -- FibonacciActionResult action_result
    -- FibonacciActionFeedback action_feedback
    -- 
    -- ================================================================================
    -- MSG: actionlib_tutorials/FibonacciActionGoal
    -- # ====== DO NOT MODIFY! AUTOGENERATED FROM AN ACTION DEFINITION ======
    -- 
    -- Header header
    -- actionlib_msgs/GoalID goal_id
    -- FibonacciGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/FibonacciGoal
    -- # ====== DO NOT MODIFY! AUTOGENERATED FROM AN ACTION DEFINITION ======
    -- #goal definition
    -- int32 order
    -- 
    -- ================================================================================
    -- MSG: actionlib_tutorials/FibonacciActionResult
    -- # ====== DO NOT MODIFY! AUTOGENERATED FROM AN ACTION DEFINITION ======
    -- 
    -- Header header
    -- actionlib_msgs/GoalStatus status
    -- FibonacciResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_tutorials/FibonacciResult
    -- # ====== DO NOT MODIFY! AUTOGENERATED FROM AN ACTION DEFINITION ======
    -- #result definition
    -- int32[] sequence
    -- 
    -- ================================================================================
    -- MSG: actionlib_tutorials/FibonacciActionFeedback
    -- # ====== DO NOT MODIFY! AUTOGENERATED FROM AN ACTION DEFINITION ======
    -- 
    -- Header header
    -- actionlib_msgs/GoalStatus status
    -- FibonacciFeedback feedback
    -- 
    -- ================================================================================
    -- MSG: actionlib_tutorials/FibonacciFeedback
    -- # ====== DO NOT MODIFY! AUTOGENERATED FROM AN ACTION DEFINITION ======
    -- #feedback
    -- int32[] sequence
    -- 
    -- ================================================================================
    -- ASN.1 type for Actionlib-tutorials-Types/FibonacciAction
    Actionlib-tutorials-FibonacciAction ::= SEQUENCE
    {
        action-goal Actionlib-tutorials-FibonacciActionGoal,
        action-result Actionlib-tutorials-FibonacciActionResult,
        action-feedback Actionlib-tutorials-FibonacciActionFeedback
    }
    -- ================================================================================

    -- ================================================================================
    -- Message Actionlib-tutorials-Types/FibonacciActionFeedback
    -- ================================================================================
    -- # ====== DO NOT MODIFY! AUTOGENERATED FROM AN ACTION DEFINITION ======
    -- 
    -- Header header
    -- actionlib_msgs/GoalStatus status
    -- FibonacciFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/FibonacciFeedback
    -- # ====== DO NOT MODIFY! AUTOGENERATED FROM AN ACTION DEFINITION ======
    -- #feedback
    -- int32[] sequence
    -- 
    -- ================================================================================
    -- ASN.1 type for Actionlib-tutorials-Types/FibonacciActionFeedback
    Actionlib-tutorials-FibonacciActionFeedback ::= SEQUENCE
    {
        header Std-msgs-Header,
        status Actionlib-msgs-GoalStatus,
        feedback Actionlib-tutorials-FibonacciFeedback
    }
    -- ================================================================================

    -- ================================================================================
    -- Message Actionlib-tutorials-Types/FibonacciActionGoal
    -- ================================================================================
    -- # ====== DO NOT MODIFY! AUTOGENERATED FROM AN ACTION DEFINITION ======
    -- 
    -- Header header
    -- actionlib_msgs/GoalID goal_id
    -- FibonacciGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/FibonacciGoal
    -- # ====== DO NOT MODIFY! AUTOGENERATED FROM AN ACTION DEFINITION ======
    -- #goal definition
    -- int32 order
    -- ================================================================================
    -- ASN.1 type for Actionlib-tutorials-Types/FibonacciActionGoal
    Actionlib-tutorials-FibonacciActionGoal ::= SEQUENCE
    {
        header Std-msgs-Header,
        goal-id Actionlib-msgs-GoalID,
        goal Actionlib-tutorials-FibonacciGoal
    }
    -- ================================================================================

    -- ================================================================================
    -- Message Actionlib-tutorials-Types/FibonacciActionResult
    -- ================================================================================
    -- # ====== DO NOT MODIFY! AUTOGENERATED FROM AN ACTION DEFINITION ======
    -- 
    -- Header header
    -- actionlib_msgs/GoalStatus status
    -- FibonacciResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib_tutorials/FibonacciResult
    -- # ====== DO NOT MODIFY! AUTOGENERATED FROM AN ACTION DEFINITION ======
    -- #result definition
    -- int32[] sequence
    -- ================================================================================
    -- ASN.1 type for Actionlib-tutorials-Types/FibonacciActionResult
    Actionlib-tutorials-FibonacciActionResult ::= SEQUENCE
    {
        header Std-msgs-Header,
        status Actionlib-msgs-GoalStatus,
        result Actionlib-tutorials-FibonacciResult
    }
    -- ================================================================================

    -- ================================================================================
    -- Message Actionlib-tutorials-Types/FibonacciFeedback
    -- ================================================================================
    -- # ====== DO NOT MODIFY! AUTOGENERATED FROM AN ACTION DEFINITION ======
    -- #feedback
    -- int32[] sequence
    -- 
    -- ================================================================================
    -- ASN.1 type for Actionlib-tutorials-Types/FibonacciFeedback
    Actionlib-tutorials-FibonacciFeedback ::= SEQUENCE (SIZE(0..max-Actionlib-tutorials-FibonacciFeedback)) OF T-Int32
    -- ================================================================================

    -- ================================================================================
    -- Message Actionlib-tutorials-Types/FibonacciGoal
    -- ================================================================================
    -- # ====== DO NOT MODIFY! AUTOGENERATED FROM AN ACTION DEFINITION ======
    -- #goal definition
    -- int32 order
    -- ================================================================================
    -- ASN.1 type for Actionlib-tutorials-Types/FibonacciGoal
    Actionlib-tutorials-FibonacciGoal ::= T-Int32

    -- ================================================================================

    -- ================================================================================
    -- Message Actionlib-tutorials-Types/FibonacciResult
    -- ================================================================================
    -- # ====== DO NOT MODIFY! AUTOGENERATED FROM AN ACTION DEFINITION ======
    -- #result definition
    -- int32[] sequence
    -- ================================================================================
    -- ASN.1 type for Actionlib-tutorials-Types/FibonacciResult
    Actionlib-tutorials-FibonacciResult ::= SEQUENCE (SIZE(0..max-Actionlib-tutorials-FibonacciResult)) OF T-Int32
    -- ================================================================================

END
