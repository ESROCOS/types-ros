-- Generated from package.asn.mako for package diagnostic_msgs

Diagnostic-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Std-msgs-Header FROM Std-msgs-Types
max-Diagnostic-msgs-DiagnosticArray, max-Diagnostic-msgs-DiagnosticStatus, Dummy-Diagnostic-msgs-Types-T FROM UserDefs-Diagnostic-msgs-Types;
    -- ================================================================================
    -- Message Diagnostic-msgs-Types/DiagnosticArray
    -- ================================================================================
    -- # This message is used to send diagnostic information about the state of the robot
    -- Header header #for timestamp
    -- DiagnosticStatus[] status # an array of components being reported on
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: diagnostic_msgs/DiagnosticStatus
    -- # This message holds the status of an individual component of the robot.
    -- # 
    -- 
    -- # Possible levels of operations
    -- byte OK=0
    -- byte WARN=1
    -- byte ERROR=2
    -- byte STALE=3
    -- 
    -- byte level # level of operation enumerated above 
    -- string name # a description of the test/component reporting
    -- string message # a description of the status
    -- string hardware_id # a hardware unique string
    -- KeyValue[] values # an array of values associated with the status
    -- 
    -- 
    -- ================================================================================
    -- MSG: diagnostic_msgs/KeyValue
    -- string key # what to label this value when viewing
    -- string value # a value to track over time
    -- ================================================================================
    -- ASN.1 type for Diagnostic-msgs-Types/DiagnosticArray
    Diagnostic-msgs-DiagnosticArray ::= SEQUENCE
    {
        header Std-msgs-Header,
        status SEQUENCE (SIZE(0..max-Diagnostic-msgs-DiagnosticArray)) OF Diagnostic-msgs-DiagnosticStatus
    }
    -- ================================================================================

    -- ================================================================================
    -- Message Diagnostic-msgs-Types/DiagnosticStatus
    -- ================================================================================
    -- # This message holds the status of an individual component of the robot.
    -- # 
    -- 
    -- # Possible levels of operations
    -- byte OK=0
    -- byte WARN=1
    -- byte ERROR=2
    -- byte STALE=3
    -- 
    -- byte level # level of operation enumerated above 
    -- string name # a description of the test/component reporting
    -- string message # a description of the status
    -- string hardware_id # a hardware unique string
    -- KeyValue[] values # an array of values associated with the status
    -- 
    -- 
    -- ================================================================================
    -- MSG: diagnostic_msgs/KeyValue
    -- string key # what to label this value when viewing
    -- string value # a value to track over time
    -- ================================================================================
    -- ASN.1 type for Diagnostic-msgs-Types/DiagnosticStatus
    Diagnostic-msgs-DiagnosticStatus ::= SEQUENCE
    {
        level T-Int8,
        name-value T-String,
        message T-String,
        hardware-id T-String,
        values SEQUENCE (SIZE(0..max-Diagnostic-msgs-DiagnosticStatus)) OF Diagnostic-msgs-KeyValue
    }
    -- ================================================================================

    -- ================================================================================
    -- Message Diagnostic-msgs-Types/KeyValue
    -- ================================================================================
    -- string key # what to label this value when viewing
    -- string value # a value to track over time
    -- ================================================================================
    -- ASN.1 type for Diagnostic-msgs-Types/KeyValue
    Diagnostic-msgs-KeyValue ::= SEQUENCE
    {
        key T-String,
        value T-String
    }
    -- ================================================================================

END
