-- Generated from package.asn.mako for package actionlib

Actionlib-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Actionlib-msgs-GoalID, Actionlib-msgs-GoalStatus FROM Actionlib-msgs-Types
Std-msgs-Header FROM Std-msgs-Types
;
    -- ================================================================================
    -- Message Actionlib-Types/TestAction
    -- ================================================================================
    -- # ====== DO NOT MODIFY! AUTOGENERATED FROM AN ACTION DEFINITION ======
    -- 
    -- TestActionGoal action_goal
    -- TestActionResult action_result
    -- TestActionFeedback action_feedback
    -- 
    -- ================================================================================
    -- MSG: actionlib/TestActionGoal
    -- # ====== DO NOT MODIFY! AUTOGENERATED FROM AN ACTION DEFINITION ======
    -- 
    -- Header header
    -- actionlib_msgs/GoalID goal_id
    -- TestGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestGoal
    -- # ====== DO NOT MODIFY! AUTOGENERATED FROM AN ACTION DEFINITION ======
    -- int32 goal
    -- 
    -- ================================================================================
    -- MSG: actionlib/TestActionResult
    -- # ====== DO NOT MODIFY! AUTOGENERATED FROM AN ACTION DEFINITION ======
    -- 
    -- Header header
    -- actionlib_msgs/GoalStatus status
    -- TestResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib/TestResult
    -- # ====== DO NOT MODIFY! AUTOGENERATED FROM AN ACTION DEFINITION ======
    -- int32 result
    -- 
    -- ================================================================================
    -- MSG: actionlib/TestActionFeedback
    -- # ====== DO NOT MODIFY! AUTOGENERATED FROM AN ACTION DEFINITION ======
    -- 
    -- Header header
    -- actionlib_msgs/GoalStatus status
    -- TestFeedback feedback
    -- 
    -- ================================================================================
    -- MSG: actionlib/TestFeedback
    -- # ====== DO NOT MODIFY! AUTOGENERATED FROM AN ACTION DEFINITION ======
    -- int32 feedback
    -- 
    -- ================================================================================
    -- ASN.1 type for Actionlib-Types/TestAction
    Actionlib-TestAction ::= SEQUENCE
    {
        action-goal Actionlib-TestActionGoal,
        action-result Actionlib-TestActionResult,
        action-feedback Actionlib-TestActionFeedback
    }
    -- ================================================================================

    -- ================================================================================
    -- Message Actionlib-Types/TestActionFeedback
    -- ================================================================================
    -- # ====== DO NOT MODIFY! AUTOGENERATED FROM AN ACTION DEFINITION ======
    -- 
    -- Header header
    -- actionlib_msgs/GoalStatus status
    -- TestFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestFeedback
    -- # ====== DO NOT MODIFY! AUTOGENERATED FROM AN ACTION DEFINITION ======
    -- int32 feedback
    -- 
    -- ================================================================================
    -- ASN.1 type for Actionlib-Types/TestActionFeedback
    Actionlib-TestActionFeedback ::= SEQUENCE
    {
        header Std-msgs-Header,
        status Actionlib-msgs-GoalStatus,
        feedback Actionlib-TestFeedback
    }
    -- ================================================================================

    -- ================================================================================
    -- Message Actionlib-Types/TestActionGoal
    -- ================================================================================
    -- # ====== DO NOT MODIFY! AUTOGENERATED FROM AN ACTION DEFINITION ======
    -- 
    -- Header header
    -- actionlib_msgs/GoalID goal_id
    -- TestGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestGoal
    -- # ====== DO NOT MODIFY! AUTOGENERATED FROM AN ACTION DEFINITION ======
    -- int32 goal
    -- ================================================================================
    -- ASN.1 type for Actionlib-Types/TestActionGoal
    Actionlib-TestActionGoal ::= SEQUENCE
    {
        header Std-msgs-Header,
        goal-id Actionlib-msgs-GoalID,
        goal Actionlib-TestGoal
    }
    -- ================================================================================

    -- ================================================================================
    -- Message Actionlib-Types/TestActionResult
    -- ================================================================================
    -- # ====== DO NOT MODIFY! AUTOGENERATED FROM AN ACTION DEFINITION ======
    -- 
    -- Header header
    -- actionlib_msgs/GoalStatus status
    -- TestResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestResult
    -- # ====== DO NOT MODIFY! AUTOGENERATED FROM AN ACTION DEFINITION ======
    -- int32 result
    -- ================================================================================
    -- ASN.1 type for Actionlib-Types/TestActionResult
    Actionlib-TestActionResult ::= SEQUENCE
    {
        header Std-msgs-Header,
        status Actionlib-msgs-GoalStatus,
        result Actionlib-TestResult
    }
    -- ================================================================================

    -- ================================================================================
    -- Message Actionlib-Types/TestFeedback
    -- ================================================================================
    -- # ====== DO NOT MODIFY! AUTOGENERATED FROM AN ACTION DEFINITION ======
    -- int32 feedback
    -- 
    -- ================================================================================
    -- ASN.1 type for Actionlib-Types/TestFeedback
    Actionlib-TestFeedback ::= T-Int32

    -- ================================================================================

    -- ================================================================================
    -- Message Actionlib-Types/TestGoal
    -- ================================================================================
    -- # ====== DO NOT MODIFY! AUTOGENERATED FROM AN ACTION DEFINITION ======
    -- int32 goal
    -- ================================================================================
    -- ASN.1 type for Actionlib-Types/TestGoal
    Actionlib-TestGoal ::= T-Int32

    -- ================================================================================

    -- ================================================================================
    -- Message Actionlib-Types/TestRequestAction
    -- ================================================================================
    -- # ====== DO NOT MODIFY! AUTOGENERATED FROM AN ACTION DEFINITION ======
    -- 
    -- TestRequestActionGoal action_goal
    -- TestRequestActionResult action_result
    -- TestRequestActionFeedback action_feedback
    -- 
    -- ================================================================================
    -- MSG: actionlib/TestRequestActionGoal
    -- # ====== DO NOT MODIFY! AUTOGENERATED FROM AN ACTION DEFINITION ======
    -- 
    -- Header header
    -- actionlib_msgs/GoalID goal_id
    -- TestRequestGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestRequestGoal
    -- # ====== DO NOT MODIFY! AUTOGENERATED FROM AN ACTION DEFINITION ======
    -- int32 TERMINATE_SUCCESS = 0
    -- int32 TERMINATE_ABORTED = 1
    -- int32 TERMINATE_REJECTED = 2
    -- int32 TERMINATE_LOSE = 3
    -- int32 TERMINATE_DROP = 4
    -- int32 TERMINATE_EXCEPTION = 5
    -- int32 terminate_status
    -- bool ignore_cancel  # If true, ignores requests to cancel
    -- string result_text
    -- int32 the_result    # Desired value for the_result in the Result
    -- bool is_simple_client
    -- duration delay_accept  # Delays accepting the goal by this amount of time
    -- duration delay_terminate  # Delays terminating for this amount of time
    -- duration pause_status  # Pauses the status messages for this amount of time
    -- 
    -- ================================================================================
    -- MSG: actionlib/TestRequestActionResult
    -- # ====== DO NOT MODIFY! AUTOGENERATED FROM AN ACTION DEFINITION ======
    -- 
    -- Header header
    -- actionlib_msgs/GoalStatus status
    -- TestRequestResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib/TestRequestResult
    -- # ====== DO NOT MODIFY! AUTOGENERATED FROM AN ACTION DEFINITION ======
    -- int32 the_result
    -- bool is_simple_server
    -- 
    -- ================================================================================
    -- MSG: actionlib/TestRequestActionFeedback
    -- # ====== DO NOT MODIFY! AUTOGENERATED FROM AN ACTION DEFINITION ======
    -- 
    -- Header header
    -- actionlib_msgs/GoalStatus status
    -- TestRequestFeedback feedback
    -- 
    -- ================================================================================
    -- MSG: actionlib/TestRequestFeedback
    -- # ====== DO NOT MODIFY! AUTOGENERATED FROM AN ACTION DEFINITION ======
    -- 
    -- ================================================================================
    -- ASN.1 type for Actionlib-Types/TestRequestAction
    Actionlib-TestRequestAction ::= SEQUENCE
    {
        action-goal Actionlib-TestRequestActionGoal,
        action-result Actionlib-TestRequestActionResult,
        action-feedback Actionlib-TestRequestActionFeedback
    }
    -- ================================================================================

    -- ================================================================================
    -- Message Actionlib-Types/TestRequestActionFeedback
    -- ================================================================================
    -- # ====== DO NOT MODIFY! AUTOGENERATED FROM AN ACTION DEFINITION ======
    -- 
    -- Header header
    -- actionlib_msgs/GoalStatus status
    -- TestRequestFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestRequestFeedback
    -- # ====== DO NOT MODIFY! AUTOGENERATED FROM AN ACTION DEFINITION ======
    -- 
    -- ================================================================================
    -- ASN.1 type for Actionlib-Types/TestRequestActionFeedback
    Actionlib-TestRequestActionFeedback ::= SEQUENCE
    {
        header Std-msgs-Header,
        status Actionlib-msgs-GoalStatus,
        feedback Actionlib-TestRequestFeedback
    }
    -- ================================================================================

    -- ================================================================================
    -- Message Actionlib-Types/TestRequestActionGoal
    -- ================================================================================
    -- # ====== DO NOT MODIFY! AUTOGENERATED FROM AN ACTION DEFINITION ======
    -- 
    -- Header header
    -- actionlib_msgs/GoalID goal_id
    -- TestRequestGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestRequestGoal
    -- # ====== DO NOT MODIFY! AUTOGENERATED FROM AN ACTION DEFINITION ======
    -- int32 TERMINATE_SUCCESS = 0
    -- int32 TERMINATE_ABORTED = 1
    -- int32 TERMINATE_REJECTED = 2
    -- int32 TERMINATE_LOSE = 3
    -- int32 TERMINATE_DROP = 4
    -- int32 TERMINATE_EXCEPTION = 5
    -- int32 terminate_status
    -- bool ignore_cancel  # If true, ignores requests to cancel
    -- string result_text
    -- int32 the_result    # Desired value for the_result in the Result
    -- bool is_simple_client
    -- duration delay_accept  # Delays accepting the goal by this amount of time
    -- duration delay_terminate  # Delays terminating for this amount of time
    -- duration pause_status  # Pauses the status messages for this amount of time
    -- ================================================================================
    -- ASN.1 type for Actionlib-Types/TestRequestActionGoal
    Actionlib-TestRequestActionGoal ::= SEQUENCE
    {
        header Std-msgs-Header,
        goal-id Actionlib-msgs-GoalID,
        goal Actionlib-TestRequestGoal
    }
    -- ================================================================================

    -- ================================================================================
    -- Message Actionlib-Types/TestRequestActionResult
    -- ================================================================================
    -- # ====== DO NOT MODIFY! AUTOGENERATED FROM AN ACTION DEFINITION ======
    -- 
    -- Header header
    -- actionlib_msgs/GoalStatus status
    -- TestRequestResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TestRequestResult
    -- # ====== DO NOT MODIFY! AUTOGENERATED FROM AN ACTION DEFINITION ======
    -- int32 the_result
    -- bool is_simple_server
    -- ================================================================================
    -- ASN.1 type for Actionlib-Types/TestRequestActionResult
    Actionlib-TestRequestActionResult ::= SEQUENCE
    {
        header Std-msgs-Header,
        status Actionlib-msgs-GoalStatus,
        result Actionlib-TestRequestResult
    }
    -- ================================================================================

    -- ================================================================================
    -- Message Actionlib-Types/TestRequestFeedback
    -- ================================================================================
    -- # ====== DO NOT MODIFY! AUTOGENERATED FROM AN ACTION DEFINITION ======
    -- 
    -- ================================================================================
    -- ASN.1 type for Actionlib-Types/TestRequestFeedback
    Actionlib-TestRequestFeedback ::= SEQUENCE
    {
    }
    -- ================================================================================

    -- ================================================================================
    -- Message Actionlib-Types/TestRequestGoal
    -- ================================================================================
    -- # ====== DO NOT MODIFY! AUTOGENERATED FROM AN ACTION DEFINITION ======
    -- int32 TERMINATE_SUCCESS = 0
    -- int32 TERMINATE_ABORTED = 1
    -- int32 TERMINATE_REJECTED = 2
    -- int32 TERMINATE_LOSE = 3
    -- int32 TERMINATE_DROP = 4
    -- int32 TERMINATE_EXCEPTION = 5
    -- int32 terminate_status
    -- bool ignore_cancel  # If true, ignores requests to cancel
    -- string result_text
    -- int32 the_result    # Desired value for the_result in the Result
    -- bool is_simple_client
    -- duration delay_accept  # Delays accepting the goal by this amount of time
    -- duration delay_terminate  # Delays terminating for this amount of time
    -- duration pause_status  # Pauses the status messages for this amount of time
    -- ================================================================================
    -- ASN.1 type for Actionlib-Types/TestRequestGoal
    Actionlib-TestRequestGoal ::= SEQUENCE
    {
        terminate-status T-Int32,
        ignore-cancel T-Boolean,
        result-text T-String,
        the-result T-Int32,
        is-simple-client T-Boolean,
        delay-accept T-Time,
        delay-terminate T-Time,
        pause-status T-Time
    }
    -- ================================================================================

    -- ================================================================================
    -- Message Actionlib-Types/TestRequestResult
    -- ================================================================================
    -- # ====== DO NOT MODIFY! AUTOGENERATED FROM AN ACTION DEFINITION ======
    -- int32 the_result
    -- bool is_simple_server
    -- ================================================================================
    -- ASN.1 type for Actionlib-Types/TestRequestResult
    Actionlib-TestRequestResult ::= SEQUENCE
    {
        the-result T-Int32,
        is-simple-server T-Boolean
    }
    -- ================================================================================

    -- ================================================================================
    -- Message Actionlib-Types/TestResult
    -- ================================================================================
    -- # ====== DO NOT MODIFY! AUTOGENERATED FROM AN ACTION DEFINITION ======
    -- int32 result
    -- ================================================================================
    -- ASN.1 type for Actionlib-Types/TestResult
    Actionlib-TestResult ::= T-Int32

    -- ================================================================================

    -- ================================================================================
    -- Message Actionlib-Types/TwoIntsAction
    -- ================================================================================
    -- # ====== DO NOT MODIFY! AUTOGENERATED FROM AN ACTION DEFINITION ======
    -- 
    -- TwoIntsActionGoal action_goal
    -- TwoIntsActionResult action_result
    -- TwoIntsActionFeedback action_feedback
    -- 
    -- ================================================================================
    -- MSG: actionlib/TwoIntsActionGoal
    -- # ====== DO NOT MODIFY! AUTOGENERATED FROM AN ACTION DEFINITION ======
    -- 
    -- Header header
    -- actionlib_msgs/GoalID goal_id
    -- TwoIntsGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TwoIntsGoal
    -- # ====== DO NOT MODIFY! AUTOGENERATED FROM AN ACTION DEFINITION ======
    -- int64 a
    -- int64 b
    -- 
    -- ================================================================================
    -- MSG: actionlib/TwoIntsActionResult
    -- # ====== DO NOT MODIFY! AUTOGENERATED FROM AN ACTION DEFINITION ======
    -- 
    -- Header header
    -- actionlib_msgs/GoalStatus status
    -- TwoIntsResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib/TwoIntsResult
    -- # ====== DO NOT MODIFY! AUTOGENERATED FROM AN ACTION DEFINITION ======
    -- int64 sum
    -- 
    -- ================================================================================
    -- MSG: actionlib/TwoIntsActionFeedback
    -- # ====== DO NOT MODIFY! AUTOGENERATED FROM AN ACTION DEFINITION ======
    -- 
    -- Header header
    -- actionlib_msgs/GoalStatus status
    -- TwoIntsFeedback feedback
    -- 
    -- ================================================================================
    -- MSG: actionlib/TwoIntsFeedback
    -- # ====== DO NOT MODIFY! AUTOGENERATED FROM AN ACTION DEFINITION ======
    -- 
    -- ================================================================================
    -- ASN.1 type for Actionlib-Types/TwoIntsAction
    Actionlib-TwoIntsAction ::= SEQUENCE
    {
        action-goal Actionlib-TwoIntsActionGoal,
        action-result Actionlib-TwoIntsActionResult,
        action-feedback Actionlib-TwoIntsActionFeedback
    }
    -- ================================================================================

    -- ================================================================================
    -- Message Actionlib-Types/TwoIntsActionFeedback
    -- ================================================================================
    -- # ====== DO NOT MODIFY! AUTOGENERATED FROM AN ACTION DEFINITION ======
    -- 
    -- Header header
    -- actionlib_msgs/GoalStatus status
    -- TwoIntsFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TwoIntsFeedback
    -- # ====== DO NOT MODIFY! AUTOGENERATED FROM AN ACTION DEFINITION ======
    -- 
    -- ================================================================================
    -- ASN.1 type for Actionlib-Types/TwoIntsActionFeedback
    Actionlib-TwoIntsActionFeedback ::= SEQUENCE
    {
        header Std-msgs-Header,
        status Actionlib-msgs-GoalStatus,
        feedback Actionlib-TwoIntsFeedback
    }
    -- ================================================================================

    -- ================================================================================
    -- Message Actionlib-Types/TwoIntsActionGoal
    -- ================================================================================
    -- # ====== DO NOT MODIFY! AUTOGENERATED FROM AN ACTION DEFINITION ======
    -- 
    -- Header header
    -- actionlib_msgs/GoalID goal_id
    -- TwoIntsGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TwoIntsGoal
    -- # ====== DO NOT MODIFY! AUTOGENERATED FROM AN ACTION DEFINITION ======
    -- int64 a
    -- int64 b
    -- ================================================================================
    -- ASN.1 type for Actionlib-Types/TwoIntsActionGoal
    Actionlib-TwoIntsActionGoal ::= SEQUENCE
    {
        header Std-msgs-Header,
        goal-id Actionlib-msgs-GoalID,
        goal Actionlib-TwoIntsGoal
    }
    -- ================================================================================

    -- ================================================================================
    -- Message Actionlib-Types/TwoIntsActionResult
    -- ================================================================================
    -- # ====== DO NOT MODIFY! AUTOGENERATED FROM AN ACTION DEFINITION ======
    -- 
    -- Header header
    -- actionlib_msgs/GoalStatus status
    -- TwoIntsResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: actionlib/TwoIntsResult
    -- # ====== DO NOT MODIFY! AUTOGENERATED FROM AN ACTION DEFINITION ======
    -- int64 sum
    -- ================================================================================
    -- ASN.1 type for Actionlib-Types/TwoIntsActionResult
    Actionlib-TwoIntsActionResult ::= SEQUENCE
    {
        header Std-msgs-Header,
        status Actionlib-msgs-GoalStatus,
        result Actionlib-TwoIntsResult
    }
    -- ================================================================================

    -- ================================================================================
    -- Message Actionlib-Types/TwoIntsFeedback
    -- ================================================================================
    -- # ====== DO NOT MODIFY! AUTOGENERATED FROM AN ACTION DEFINITION ======
    -- 
    -- ================================================================================
    -- ASN.1 type for Actionlib-Types/TwoIntsFeedback
    Actionlib-TwoIntsFeedback ::= SEQUENCE
    {
    }
    -- ================================================================================

    -- ================================================================================
    -- Message Actionlib-Types/TwoIntsGoal
    -- ================================================================================
    -- # ====== DO NOT MODIFY! AUTOGENERATED FROM AN ACTION DEFINITION ======
    -- int64 a
    -- int64 b
    -- ================================================================================
    -- ASN.1 type for Actionlib-Types/TwoIntsGoal
    Actionlib-TwoIntsGoal ::= SEQUENCE
    {
        a T-Int64,
        b T-Int64
    }
    -- ================================================================================

    -- ================================================================================
    -- Message Actionlib-Types/TwoIntsResult
    -- ================================================================================
    -- # ====== DO NOT MODIFY! AUTOGENERATED FROM AN ACTION DEFINITION ======
    -- int64 sum
    -- ================================================================================
    -- ASN.1 type for Actionlib-Types/TwoIntsResult
    Actionlib-TwoIntsResult ::= T-Int64

    -- ================================================================================

END
