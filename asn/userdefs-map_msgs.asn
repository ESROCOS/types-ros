-- Generated from userdefs.asn.mako for package map_msgs

UserDefs-Map-msgs-Types DEFINITIONS ::=
BEGIN

IMPORTS T-UInt32 FROM TASTE-BasicTypes;

    -- Dummy type (TASTE doesn't handle the includes correctly if an ASN.1 file defines only constants)
    Dummy-Map-msgs-Types-T ::= T-UInt32

    -- Size constants definitions: to be set according to the application's needs

    -- Size constant for type Map-msgs-OccupancyGridUpdate
    max-Map-msgs-OccupancyGridUpdate T-UInt32 ::= 60

END
