-- Generated from package.asn.mako for package control_msgs

Control-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-PointStamped, Geometry-msgs-Vector3 FROM Geometry-msgs-Types
Actionlib-msgs-GoalID, Actionlib-msgs-GoalStatus FROM Actionlib-msgs-Types
Trajectory-msgs-JointTrajectory, Trajectory-msgs-JointTrajectoryPoint FROM Trajectory-msgs-Types
Std-msgs-Header FROM Std-msgs-Types
max-Control-msgs-JointTrajectoryControllerState, max-Control-msgs-FollowJointTrajectoryFeedback, max-Control-msgs-FollowJointTrajectoryGoal, Dummy-Control-msgs-Types-T FROM UserDefs-Control-msgs-Types;
    -- ================================================================================
    -- Message Control-msgs-Types/FollowJointTrajectoryAction
    -- ================================================================================
    -- # ====== DO NOT MODIFY! AUTOGENERATED FROM AN ACTION DEFINITION ======
    -- 
    -- FollowJointTrajectoryActionGoal action_goal
    -- FollowJointTrajectoryActionResult action_result
    -- FollowJointTrajectoryActionFeedback action_feedback
    -- 
    -- ================================================================================
    -- MSG: control_msgs/FollowJointTrajectoryActionGoal
    -- # ====== DO NOT MODIFY! AUTOGENERATED FROM AN ACTION DEFINITION ======
    -- 
    -- Header header
    -- actionlib_msgs/GoalID goal_id
    -- FollowJointTrajectoryGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/FollowJointTrajectoryGoal
    -- # ====== DO NOT MODIFY! AUTOGENERATED FROM AN ACTION DEFINITION ======
    -- # The joint trajectory to follow
    -- trajectory_msgs/JointTrajectory trajectory
    -- 
    -- # Tolerances for the trajectory.  If the measured joint values fall
    -- # outside the tolerances the trajectory goal is aborted.  Any
    -- # tolerances that are not specified (by being omitted or set to 0) are
    -- # set to the defaults for the action server (often taken from the
    -- # parameter server).
    -- 
    -- # Tolerances applied to the joints as the trajectory is executed.  If
    -- # violated, the goal aborts with error_code set to
    -- # PATH_TOLERANCE_VIOLATED.
    -- JointTolerance[] path_tolerance
    -- 
    -- # To report success, the joints must be within goal_tolerance of the
    -- # final trajectory value.  The goal must be achieved by time the
    -- # trajectory ends plus goal_time_tolerance.  (goal_time_tolerance
    -- # allows some leeway in time, so that the trajectory goal can still
    -- # succeed even if the joints reach the goal some time after the
    -- # precise end time of the trajectory).
    -- #
    -- # If the joints are not within goal_tolerance after "trajectory finish
    -- # time" + goal_time_tolerance, the goal aborts with error_code set to
    -- # GOAL_TOLERANCE_VIOLATED
    -- JointTolerance[] goal_tolerance
    -- duration goal_time_tolerance
    -- 
    -- 
    -- ================================================================================
    -- MSG: trajectory_msgs/JointTrajectory
    -- Header header
    -- string[] joint_names
    -- JointTrajectoryPoint[] points
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- 
    -- ================================================================================
    -- MSG: control_msgs/JointTolerance
    -- # The tolerances specify the amount the position, velocity, and
    -- # accelerations can vary from the setpoints.  For example, in the case
    -- # of trajectory control, when the actual position varies beyond
    -- # (desired position + position tolerance), the trajectory goal may
    -- # abort.
    -- # 
    -- # There are two special values for tolerances:
    -- #  * 0 - The tolerance is unspecified and will remain at whatever the default is
    -- #  * -1 - The tolerance is "erased".  If there was a default, the joint will be
    -- #         allowed to move without restriction.
    -- 
    -- string name
    -- float64 position  # in radians or meters (for a revolute or prismatic joint, respectively)
    -- float64 velocity  # in rad/sec or m/sec
    -- float64 acceleration  # in rad/sec^2 or m/sec^2
    -- 
    -- ================================================================================
    -- MSG: control_msgs/FollowJointTrajectoryActionResult
    -- # ====== DO NOT MODIFY! AUTOGENERATED FROM AN ACTION DEFINITION ======
    -- 
    -- Header header
    -- actionlib_msgs/GoalStatus status
    -- FollowJointTrajectoryResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: control_msgs/FollowJointTrajectoryResult
    -- # ====== DO NOT MODIFY! AUTOGENERATED FROM AN ACTION DEFINITION ======
    -- int32 error_code
    -- int32 SUCCESSFUL = 0
    -- int32 INVALID_GOAL = -1
    -- int32 INVALID_JOINTS = -2
    -- int32 OLD_HEADER_TIMESTAMP = -3
    -- int32 PATH_TOLERANCE_VIOLATED = -4
    -- int32 GOAL_TOLERANCE_VIOLATED = -5
    -- 
    -- # Human readable description of the error code. Contains complementary
    -- # information that is especially useful when execution fails, for instance:
    -- # - INVALID_GOAL: The reason for the invalid goal (e.g., the requested
    -- #   trajectory is in the past).
    -- # - INVALID_JOINTS: The mismatch between the expected controller joints
    -- #   and those provided in the goal.
    -- # - PATH_TOLERANCE_VIOLATED and GOAL_TOLERANCE_VIOLATED: Which joint
    -- #   violated which tolerance, and by how much.
    -- string error_string
    -- 
    -- 
    -- ================================================================================
    -- MSG: control_msgs/FollowJointTrajectoryActionFeedback
    -- # ====== DO NOT MODIFY! AUTOGENERATED FROM AN ACTION DEFINITION ======
    -- 
    -- Header header
    -- actionlib_msgs/GoalStatus status
    -- FollowJointTrajectoryFeedback feedback
    -- 
    -- ================================================================================
    -- MSG: control_msgs/FollowJointTrajectoryFeedback
    -- # ====== DO NOT MODIFY! AUTOGENERATED FROM AN ACTION DEFINITION ======
    -- Header header
    -- string[] joint_names
    -- trajectory_msgs/JointTrajectoryPoint desired
    -- trajectory_msgs/JointTrajectoryPoint actual
    -- trajectory_msgs/JointTrajectoryPoint error
    -- 
    -- ================================================================================
    -- ASN.1 type for Control-msgs-Types/FollowJointTrajectoryAction
    Control-msgs-FollowJointTrajectoryAction ::= SEQUENCE
    {
        action-goal Control-msgs-FollowJointTrajectoryActionGoal,
        action-result Control-msgs-FollowJointTrajectoryActionResult,
        action-feedback Control-msgs-FollowJointTrajectoryActionFeedback
    }
    -- ================================================================================

    -- ================================================================================
    -- Message Control-msgs-Types/FollowJointTrajectoryActionFeedback
    -- ================================================================================
    -- # ====== DO NOT MODIFY! AUTOGENERATED FROM AN ACTION DEFINITION ======
    -- 
    -- Header header
    -- actionlib_msgs/GoalStatus status
    -- FollowJointTrajectoryFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/FollowJointTrajectoryFeedback
    -- # ====== DO NOT MODIFY! AUTOGENERATED FROM AN ACTION DEFINITION ======
    -- Header header
    -- string[] joint_names
    -- trajectory_msgs/JointTrajectoryPoint desired
    -- trajectory_msgs/JointTrajectoryPoint actual
    -- trajectory_msgs/JointTrajectoryPoint error
    -- 
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Control-msgs-Types/FollowJointTrajectoryActionFeedback
    Control-msgs-FollowJointTrajectoryActionFeedback ::= SEQUENCE
    {
        header Std-msgs-Header,
        status Actionlib-msgs-GoalStatus,
        feedback Control-msgs-FollowJointTrajectoryFeedback
    }
    -- ================================================================================

    -- ================================================================================
    -- Message Control-msgs-Types/FollowJointTrajectoryActionGoal
    -- ================================================================================
    -- # ====== DO NOT MODIFY! AUTOGENERATED FROM AN ACTION DEFINITION ======
    -- 
    -- Header header
    -- actionlib_msgs/GoalID goal_id
    -- FollowJointTrajectoryGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/FollowJointTrajectoryGoal
    -- # ====== DO NOT MODIFY! AUTOGENERATED FROM AN ACTION DEFINITION ======
    -- # The joint trajectory to follow
    -- trajectory_msgs/JointTrajectory trajectory
    -- 
    -- # Tolerances for the trajectory.  If the measured joint values fall
    -- # outside the tolerances the trajectory goal is aborted.  Any
    -- # tolerances that are not specified (by being omitted or set to 0) are
    -- # set to the defaults for the action server (often taken from the
    -- # parameter server).
    -- 
    -- # Tolerances applied to the joints as the trajectory is executed.  If
    -- # violated, the goal aborts with error_code set to
    -- # PATH_TOLERANCE_VIOLATED.
    -- JointTolerance[] path_tolerance
    -- 
    -- # To report success, the joints must be within goal_tolerance of the
    -- # final trajectory value.  The goal must be achieved by time the
    -- # trajectory ends plus goal_time_tolerance.  (goal_time_tolerance
    -- # allows some leeway in time, so that the trajectory goal can still
    -- # succeed even if the joints reach the goal some time after the
    -- # precise end time of the trajectory).
    -- #
    -- # If the joints are not within goal_tolerance after "trajectory finish
    -- # time" + goal_time_tolerance, the goal aborts with error_code set to
    -- # GOAL_TOLERANCE_VIOLATED
    -- JointTolerance[] goal_tolerance
    -- duration goal_time_tolerance
    -- 
    -- 
    -- ================================================================================
    -- MSG: trajectory_msgs/JointTrajectory
    -- Header header
    -- string[] joint_names
    -- JointTrajectoryPoint[] points
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- 
    -- ================================================================================
    -- MSG: control_msgs/JointTolerance
    -- # The tolerances specify the amount the position, velocity, and
    -- # accelerations can vary from the setpoints.  For example, in the case
    -- # of trajectory control, when the actual position varies beyond
    -- # (desired position + position tolerance), the trajectory goal may
    -- # abort.
    -- # 
    -- # There are two special values for tolerances:
    -- #  * 0 - The tolerance is unspecified and will remain at whatever the default is
    -- #  * -1 - The tolerance is "erased".  If there was a default, the joint will be
    -- #         allowed to move without restriction.
    -- 
    -- string name
    -- float64 position  # in radians or meters (for a revolute or prismatic joint, respectively)
    -- float64 velocity  # in rad/sec or m/sec
    -- float64 acceleration  # in rad/sec^2 or m/sec^2
    -- ================================================================================
    -- ASN.1 type for Control-msgs-Types/FollowJointTrajectoryActionGoal
    Control-msgs-FollowJointTrajectoryActionGoal ::= SEQUENCE
    {
        header Std-msgs-Header,
        goal-id Actionlib-msgs-GoalID,
        goal Control-msgs-FollowJointTrajectoryGoal
    }
    -- ================================================================================

    -- ================================================================================
    -- Message Control-msgs-Types/FollowJointTrajectoryActionResult
    -- ================================================================================
    -- # ====== DO NOT MODIFY! AUTOGENERATED FROM AN ACTION DEFINITION ======
    -- 
    -- Header header
    -- actionlib_msgs/GoalStatus status
    -- FollowJointTrajectoryResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/FollowJointTrajectoryResult
    -- # ====== DO NOT MODIFY! AUTOGENERATED FROM AN ACTION DEFINITION ======
    -- int32 error_code
    -- int32 SUCCESSFUL = 0
    -- int32 INVALID_GOAL = -1
    -- int32 INVALID_JOINTS = -2
    -- int32 OLD_HEADER_TIMESTAMP = -3
    -- int32 PATH_TOLERANCE_VIOLATED = -4
    -- int32 GOAL_TOLERANCE_VIOLATED = -5
    -- 
    -- # Human readable description of the error code. Contains complementary
    -- # information that is especially useful when execution fails, for instance:
    -- # - INVALID_GOAL: The reason for the invalid goal (e.g., the requested
    -- #   trajectory is in the past).
    -- # - INVALID_JOINTS: The mismatch between the expected controller joints
    -- #   and those provided in the goal.
    -- # - PATH_TOLERANCE_VIOLATED and GOAL_TOLERANCE_VIOLATED: Which joint
    -- #   violated which tolerance, and by how much.
    -- string error_string
    -- 
    -- ================================================================================
    -- ASN.1 type for Control-msgs-Types/FollowJointTrajectoryActionResult
    Control-msgs-FollowJointTrajectoryActionResult ::= SEQUENCE
    {
        header Std-msgs-Header,
        status Actionlib-msgs-GoalStatus,
        result Control-msgs-FollowJointTrajectoryResult
    }
    -- ================================================================================

    -- ================================================================================
    -- Message Control-msgs-Types/FollowJointTrajectoryFeedback
    -- ================================================================================
    -- # ====== DO NOT MODIFY! AUTOGENERATED FROM AN ACTION DEFINITION ======
    -- Header header
    -- string[] joint_names
    -- trajectory_msgs/JointTrajectoryPoint desired
    -- trajectory_msgs/JointTrajectoryPoint actual
    -- trajectory_msgs/JointTrajectoryPoint error
    -- 
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Control-msgs-Types/FollowJointTrajectoryFeedback
    Control-msgs-FollowJointTrajectoryFeedback ::= SEQUENCE
    {
        header Std-msgs-Header,
        joint-names SEQUENCE (SIZE(0..max-Control-msgs-FollowJointTrajectoryFeedback)) OF T-String,
        desired Trajectory-msgs-JointTrajectoryPoint,
        actual Trajectory-msgs-JointTrajectoryPoint,
        error-value Trajectory-msgs-JointTrajectoryPoint
    }
    -- ================================================================================

    -- ================================================================================
    -- Message Control-msgs-Types/FollowJointTrajectoryGoal
    -- ================================================================================
    -- # ====== DO NOT MODIFY! AUTOGENERATED FROM AN ACTION DEFINITION ======
    -- # The joint trajectory to follow
    -- trajectory_msgs/JointTrajectory trajectory
    -- 
    -- # Tolerances for the trajectory.  If the measured joint values fall
    -- # outside the tolerances the trajectory goal is aborted.  Any
    -- # tolerances that are not specified (by being omitted or set to 0) are
    -- # set to the defaults for the action server (often taken from the
    -- # parameter server).
    -- 
    -- # Tolerances applied to the joints as the trajectory is executed.  If
    -- # violated, the goal aborts with error_code set to
    -- # PATH_TOLERANCE_VIOLATED.
    -- JointTolerance[] path_tolerance
    -- 
    -- # To report success, the joints must be within goal_tolerance of the
    -- # final trajectory value.  The goal must be achieved by time the
    -- # trajectory ends plus goal_time_tolerance.  (goal_time_tolerance
    -- # allows some leeway in time, so that the trajectory goal can still
    -- # succeed even if the joints reach the goal some time after the
    -- # precise end time of the trajectory).
    -- #
    -- # If the joints are not within goal_tolerance after "trajectory finish
    -- # time" + goal_time_tolerance, the goal aborts with error_code set to
    -- # GOAL_TOLERANCE_VIOLATED
    -- JointTolerance[] goal_tolerance
    -- duration goal_time_tolerance
    -- 
    -- 
    -- ================================================================================
    -- MSG: trajectory_msgs/JointTrajectory
    -- Header header
    -- string[] joint_names
    -- JointTrajectoryPoint[] points
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- 
    -- ================================================================================
    -- MSG: control_msgs/JointTolerance
    -- # The tolerances specify the amount the position, velocity, and
    -- # accelerations can vary from the setpoints.  For example, in the case
    -- # of trajectory control, when the actual position varies beyond
    -- # (desired position + position tolerance), the trajectory goal may
    -- # abort.
    -- # 
    -- # There are two special values for tolerances:
    -- #  * 0 - The tolerance is unspecified and will remain at whatever the default is
    -- #  * -1 - The tolerance is "erased".  If there was a default, the joint will be
    -- #         allowed to move without restriction.
    -- 
    -- string name
    -- float64 position  # in radians or meters (for a revolute or prismatic joint, respectively)
    -- float64 velocity  # in rad/sec or m/sec
    -- float64 acceleration  # in rad/sec^2 or m/sec^2
    -- ================================================================================
    -- ASN.1 type for Control-msgs-Types/FollowJointTrajectoryGoal
    Control-msgs-FollowJointTrajectoryGoal ::= SEQUENCE
    {
        trajectory Trajectory-msgs-JointTrajectory,
        path-tolerance SEQUENCE (SIZE(0..max-Control-msgs-FollowJointTrajectoryGoal)) OF Control-msgs-JointTolerance,
        goal-tolerance SEQUENCE (SIZE(0..max-Control-msgs-FollowJointTrajectoryGoal)) OF Control-msgs-JointTolerance,
        goal-time-tolerance T-Time
    }
    -- ================================================================================

    -- ================================================================================
    -- Message Control-msgs-Types/FollowJointTrajectoryResult
    -- ================================================================================
    -- # ====== DO NOT MODIFY! AUTOGENERATED FROM AN ACTION DEFINITION ======
    -- int32 error_code
    -- int32 SUCCESSFUL = 0
    -- int32 INVALID_GOAL = -1
    -- int32 INVALID_JOINTS = -2
    -- int32 OLD_HEADER_TIMESTAMP = -3
    -- int32 PATH_TOLERANCE_VIOLATED = -4
    -- int32 GOAL_TOLERANCE_VIOLATED = -5
    -- 
    -- # Human readable description of the error code. Contains complementary
    -- # information that is especially useful when execution fails, for instance:
    -- # - INVALID_GOAL: The reason for the invalid goal (e.g., the requested
    -- #   trajectory is in the past).
    -- # - INVALID_JOINTS: The mismatch between the expected controller joints
    -- #   and those provided in the goal.
    -- # - PATH_TOLERANCE_VIOLATED and GOAL_TOLERANCE_VIOLATED: Which joint
    -- #   violated which tolerance, and by how much.
    -- string error_string
    -- 
    -- ================================================================================
    -- ASN.1 type for Control-msgs-Types/FollowJointTrajectoryResult
    Control-msgs-FollowJointTrajectoryResult ::= SEQUENCE
    {
        error-code T-Int32,
        error-string T-String
    }
    -- ================================================================================

    -- ================================================================================
    -- Message Control-msgs-Types/GripperCommand
    -- ================================================================================
    -- float64 position
    -- float64 max_effort
    -- ================================================================================
    -- ASN.1 type for Control-msgs-Types/GripperCommand
    Control-msgs-GripperCommand ::= SEQUENCE
    {
        position T-Double,
        max-effort T-Double
    }
    -- ================================================================================

    -- ================================================================================
    -- Message Control-msgs-Types/GripperCommandAction
    -- ================================================================================
    -- # ====== DO NOT MODIFY! AUTOGENERATED FROM AN ACTION DEFINITION ======
    -- 
    -- GripperCommandActionGoal action_goal
    -- GripperCommandActionResult action_result
    -- GripperCommandActionFeedback action_feedback
    -- 
    -- ================================================================================
    -- MSG: control_msgs/GripperCommandActionGoal
    -- # ====== DO NOT MODIFY! AUTOGENERATED FROM AN ACTION DEFINITION ======
    -- 
    -- Header header
    -- actionlib_msgs/GoalID goal_id
    -- GripperCommandGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/GripperCommandGoal
    -- # ====== DO NOT MODIFY! AUTOGENERATED FROM AN ACTION DEFINITION ======
    -- GripperCommand command
    -- 
    -- ================================================================================
    -- MSG: control_msgs/GripperCommand
    -- float64 position
    -- float64 max_effort
    -- 
    -- ================================================================================
    -- MSG: control_msgs/GripperCommandActionResult
    -- # ====== DO NOT MODIFY! AUTOGENERATED FROM AN ACTION DEFINITION ======
    -- 
    -- Header header
    -- actionlib_msgs/GoalStatus status
    -- GripperCommandResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: control_msgs/GripperCommandResult
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- 
    -- ================================================================================
    -- MSG: control_msgs/GripperCommandActionFeedback
    -- # ====== DO NOT MODIFY! AUTOGENERATED FROM AN ACTION DEFINITION ======
    -- 
    -- Header header
    -- actionlib_msgs/GoalStatus status
    -- GripperCommandFeedback feedback
    -- 
    -- ================================================================================
    -- MSG: control_msgs/GripperCommandFeedback
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- 
    -- ================================================================================
    -- ASN.1 type for Control-msgs-Types/GripperCommandAction
    Control-msgs-GripperCommandAction ::= SEQUENCE
    {
        action-goal Control-msgs-GripperCommandActionGoal,
        action-result Control-msgs-GripperCommandActionResult,
        action-feedback Control-msgs-GripperCommandActionFeedback
    }
    -- ================================================================================

    -- ================================================================================
    -- Message Control-msgs-Types/GripperCommandActionFeedback
    -- ================================================================================
    -- # ====== DO NOT MODIFY! AUTOGENERATED FROM AN ACTION DEFINITION ======
    -- 
    -- Header header
    -- actionlib_msgs/GoalStatus status
    -- GripperCommandFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/GripperCommandFeedback
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- 
    -- ================================================================================
    -- ASN.1 type for Control-msgs-Types/GripperCommandActionFeedback
    Control-msgs-GripperCommandActionFeedback ::= SEQUENCE
    {
        header Std-msgs-Header,
        status Actionlib-msgs-GoalStatus,
        feedback Control-msgs-GripperCommandFeedback
    }
    -- ================================================================================

    -- ================================================================================
    -- Message Control-msgs-Types/GripperCommandActionGoal
    -- ================================================================================
    -- # ====== DO NOT MODIFY! AUTOGENERATED FROM AN ACTION DEFINITION ======
    -- 
    -- Header header
    -- actionlib_msgs/GoalID goal_id
    -- GripperCommandGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/GripperCommandGoal
    -- # ====== DO NOT MODIFY! AUTOGENERATED FROM AN ACTION DEFINITION ======
    -- GripperCommand command
    -- 
    -- ================================================================================
    -- MSG: control_msgs/GripperCommand
    -- float64 position
    -- float64 max_effort
    -- ================================================================================
    -- ASN.1 type for Control-msgs-Types/GripperCommandActionGoal
    Control-msgs-GripperCommandActionGoal ::= SEQUENCE
    {
        header Std-msgs-Header,
        goal-id Actionlib-msgs-GoalID,
        goal Control-msgs-GripperCommandGoal
    }
    -- ================================================================================

    -- ================================================================================
    -- Message Control-msgs-Types/GripperCommandActionResult
    -- ================================================================================
    -- # ====== DO NOT MODIFY! AUTOGENERATED FROM AN ACTION DEFINITION ======
    -- 
    -- Header header
    -- actionlib_msgs/GoalStatus status
    -- GripperCommandResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/GripperCommandResult
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- ================================================================================
    -- ASN.1 type for Control-msgs-Types/GripperCommandActionResult
    Control-msgs-GripperCommandActionResult ::= SEQUENCE
    {
        header Std-msgs-Header,
        status Actionlib-msgs-GoalStatus,
        result Control-msgs-GripperCommandResult
    }
    -- ================================================================================

    -- ================================================================================
    -- Message Control-msgs-Types/GripperCommandFeedback
    -- ================================================================================
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- 
    -- ================================================================================
    -- ASN.1 type for Control-msgs-Types/GripperCommandFeedback
    Control-msgs-GripperCommandFeedback ::= SEQUENCE
    {
        position T-Double,
        effort T-Double,
        stalled T-Boolean,
        reached-goal T-Boolean
    }
    -- ================================================================================

    -- ================================================================================
    -- Message Control-msgs-Types/GripperCommandGoal
    -- ================================================================================
    -- # ====== DO NOT MODIFY! AUTOGENERATED FROM AN ACTION DEFINITION ======
    -- GripperCommand command
    -- 
    -- ================================================================================
    -- MSG: control_msgs/GripperCommand
    -- float64 position
    -- float64 max_effort
    -- ================================================================================
    -- ASN.1 type for Control-msgs-Types/GripperCommandGoal
    Control-msgs-GripperCommandGoal ::= Control-msgs-GripperCommand

    -- ================================================================================

    -- ================================================================================
    -- Message Control-msgs-Types/GripperCommandResult
    -- ================================================================================
    -- # ====== DO NOT MODIFY! AUTOGENERATED FROM AN ACTION DEFINITION ======
    -- float64 position  # The current gripper gap size (in meters)
    -- float64 effort    # The current effort exerted (in Newtons)
    -- bool stalled      # True iff the gripper is exerting max effort and not moving
    -- bool reached_goal # True iff the gripper position has reached the commanded setpoint
    -- ================================================================================
    -- ASN.1 type for Control-msgs-Types/GripperCommandResult
    Control-msgs-GripperCommandResult ::= SEQUENCE
    {
        position T-Double,
        effort T-Double,
        stalled T-Boolean,
        reached-goal T-Boolean
    }
    -- ================================================================================

    -- ================================================================================
    -- Message Control-msgs-Types/JointControllerState
    -- ================================================================================
    -- Header header
    -- float64 set_point
    -- float64 process_value
    -- float64 process_value_dot
    -- float64 error
    -- float64 time_step
    -- float64 command
    -- float64 p
    -- float64 i
    -- float64 d
    -- float64 i_clamp
    -- bool antiwindup
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Control-msgs-Types/JointControllerState
    Control-msgs-JointControllerState ::= SEQUENCE
    {
        header Std-msgs-Header,
        set-point T-Double,
        process-value T-Double,
        process-value-dot T-Double,
        error-value T-Double,
        time-step T-Double,
        command T-Double,
        p T-Double,
        i-value T-Double,
        d T-Double,
        i-clamp T-Double,
        antiwindup T-Boolean
    }
    -- ================================================================================

    -- ================================================================================
    -- Message Control-msgs-Types/JointTolerance
    -- ================================================================================
    -- # The tolerances specify the amount the position, velocity, and
    -- # accelerations can vary from the setpoints.  For example, in the case
    -- # of trajectory control, when the actual position varies beyond
    -- # (desired position + position tolerance), the trajectory goal may
    -- # abort.
    -- # 
    -- # There are two special values for tolerances:
    -- #  * 0 - The tolerance is unspecified and will remain at whatever the default is
    -- #  * -1 - The tolerance is "erased".  If there was a default, the joint will be
    -- #         allowed to move without restriction.
    -- 
    -- string name
    -- float64 position  # in radians or meters (for a revolute or prismatic joint, respectively)
    -- float64 velocity  # in rad/sec or m/sec
    -- float64 acceleration  # in rad/sec^2 or m/sec^2
    -- ================================================================================
    -- ASN.1 type for Control-msgs-Types/JointTolerance
    Control-msgs-JointTolerance ::= SEQUENCE
    {
        name-value T-String,
        position T-Double,
        velocity T-Double,
        acceleration T-Double
    }
    -- ================================================================================

    -- ================================================================================
    -- Message Control-msgs-Types/JointTrajectoryAction
    -- ================================================================================
    -- # ====== DO NOT MODIFY! AUTOGENERATED FROM AN ACTION DEFINITION ======
    -- 
    -- JointTrajectoryActionGoal action_goal
    -- JointTrajectoryActionResult action_result
    -- JointTrajectoryActionFeedback action_feedback
    -- 
    -- ================================================================================
    -- MSG: control_msgs/JointTrajectoryActionGoal
    -- # ====== DO NOT MODIFY! AUTOGENERATED FROM AN ACTION DEFINITION ======
    -- 
    -- Header header
    -- actionlib_msgs/GoalID goal_id
    -- JointTrajectoryGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/JointTrajectoryGoal
    -- # ====== DO NOT MODIFY! AUTOGENERATED FROM AN ACTION DEFINITION ======
    -- trajectory_msgs/JointTrajectory trajectory
    -- 
    -- ================================================================================
    -- MSG: trajectory_msgs/JointTrajectory
    -- Header header
    -- string[] joint_names
    -- JointTrajectoryPoint[] points
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- 
    -- ================================================================================
    -- MSG: control_msgs/JointTrajectoryActionResult
    -- # ====== DO NOT MODIFY! AUTOGENERATED FROM AN ACTION DEFINITION ======
    -- 
    -- Header header
    -- actionlib_msgs/GoalStatus status
    -- JointTrajectoryResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: control_msgs/JointTrajectoryResult
    -- # ====== DO NOT MODIFY! AUTOGENERATED FROM AN ACTION DEFINITION ======
    -- 
    -- ================================================================================
    -- MSG: control_msgs/JointTrajectoryActionFeedback
    -- # ====== DO NOT MODIFY! AUTOGENERATED FROM AN ACTION DEFINITION ======
    -- 
    -- Header header
    -- actionlib_msgs/GoalStatus status
    -- JointTrajectoryFeedback feedback
    -- 
    -- ================================================================================
    -- MSG: control_msgs/JointTrajectoryFeedback
    -- # ====== DO NOT MODIFY! AUTOGENERATED FROM AN ACTION DEFINITION ======
    -- 
    -- ================================================================================
    -- ASN.1 type for Control-msgs-Types/JointTrajectoryAction
    Control-msgs-JointTrajectoryAction ::= SEQUENCE
    {
        action-goal Control-msgs-JointTrajectoryActionGoal,
        action-result Control-msgs-JointTrajectoryActionResult,
        action-feedback Control-msgs-JointTrajectoryActionFeedback
    }
    -- ================================================================================

    -- ================================================================================
    -- Message Control-msgs-Types/JointTrajectoryActionFeedback
    -- ================================================================================
    -- # ====== DO NOT MODIFY! AUTOGENERATED FROM AN ACTION DEFINITION ======
    -- 
    -- Header header
    -- actionlib_msgs/GoalStatus status
    -- JointTrajectoryFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/JointTrajectoryFeedback
    -- # ====== DO NOT MODIFY! AUTOGENERATED FROM AN ACTION DEFINITION ======
    -- 
    -- ================================================================================
    -- ASN.1 type for Control-msgs-Types/JointTrajectoryActionFeedback
    Control-msgs-JointTrajectoryActionFeedback ::= SEQUENCE
    {
        header Std-msgs-Header,
        status Actionlib-msgs-GoalStatus,
        feedback Control-msgs-JointTrajectoryFeedback
    }
    -- ================================================================================

    -- ================================================================================
    -- Message Control-msgs-Types/JointTrajectoryActionGoal
    -- ================================================================================
    -- # ====== DO NOT MODIFY! AUTOGENERATED FROM AN ACTION DEFINITION ======
    -- 
    -- Header header
    -- actionlib_msgs/GoalID goal_id
    -- JointTrajectoryGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/JointTrajectoryGoal
    -- # ====== DO NOT MODIFY! AUTOGENERATED FROM AN ACTION DEFINITION ======
    -- trajectory_msgs/JointTrajectory trajectory
    -- 
    -- ================================================================================
    -- MSG: trajectory_msgs/JointTrajectory
    -- Header header
    -- string[] joint_names
    -- JointTrajectoryPoint[] points
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Control-msgs-Types/JointTrajectoryActionGoal
    Control-msgs-JointTrajectoryActionGoal ::= SEQUENCE
    {
        header Std-msgs-Header,
        goal-id Actionlib-msgs-GoalID,
        goal Control-msgs-JointTrajectoryGoal
    }
    -- ================================================================================

    -- ================================================================================
    -- Message Control-msgs-Types/JointTrajectoryActionResult
    -- ================================================================================
    -- # ====== DO NOT MODIFY! AUTOGENERATED FROM AN ACTION DEFINITION ======
    -- 
    -- Header header
    -- actionlib_msgs/GoalStatus status
    -- JointTrajectoryResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/JointTrajectoryResult
    -- # ====== DO NOT MODIFY! AUTOGENERATED FROM AN ACTION DEFINITION ======
    -- ================================================================================
    -- ASN.1 type for Control-msgs-Types/JointTrajectoryActionResult
    Control-msgs-JointTrajectoryActionResult ::= SEQUENCE
    {
        header Std-msgs-Header,
        status Actionlib-msgs-GoalStatus,
        result Control-msgs-JointTrajectoryResult
    }
    -- ================================================================================

    -- ================================================================================
    -- Message Control-msgs-Types/JointTrajectoryControllerState
    -- ================================================================================
    -- Header header
    -- string[] joint_names
    -- trajectory_msgs/JointTrajectoryPoint desired
    -- trajectory_msgs/JointTrajectoryPoint actual
    -- trajectory_msgs/JointTrajectoryPoint error  # Redundant, but useful
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Control-msgs-Types/JointTrajectoryControllerState
    Control-msgs-JointTrajectoryControllerState ::= SEQUENCE
    {
        header Std-msgs-Header,
        joint-names SEQUENCE (SIZE(0..max-Control-msgs-JointTrajectoryControllerState)) OF T-String,
        desired Trajectory-msgs-JointTrajectoryPoint,
        actual Trajectory-msgs-JointTrajectoryPoint,
        error-value Trajectory-msgs-JointTrajectoryPoint
    }
    -- ================================================================================

    -- ================================================================================
    -- Message Control-msgs-Types/JointTrajectoryFeedback
    -- ================================================================================
    -- # ====== DO NOT MODIFY! AUTOGENERATED FROM AN ACTION DEFINITION ======
    -- 
    -- ================================================================================
    -- ASN.1 type for Control-msgs-Types/JointTrajectoryFeedback
    Control-msgs-JointTrajectoryFeedback ::= SEQUENCE
    {
    }
    -- ================================================================================

    -- ================================================================================
    -- Message Control-msgs-Types/JointTrajectoryGoal
    -- ================================================================================
    -- # ====== DO NOT MODIFY! AUTOGENERATED FROM AN ACTION DEFINITION ======
    -- trajectory_msgs/JointTrajectory trajectory
    -- 
    -- ================================================================================
    -- MSG: trajectory_msgs/JointTrajectory
    -- Header header
    -- string[] joint_names
    -- JointTrajectoryPoint[] points
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Control-msgs-Types/JointTrajectoryGoal
    Control-msgs-JointTrajectoryGoal ::= Trajectory-msgs-JointTrajectory

    -- ================================================================================

    -- ================================================================================
    -- Message Control-msgs-Types/JointTrajectoryResult
    -- ================================================================================
    -- # ====== DO NOT MODIFY! AUTOGENERATED FROM AN ACTION DEFINITION ======
    -- ================================================================================
    -- ASN.1 type for Control-msgs-Types/JointTrajectoryResult
    Control-msgs-JointTrajectoryResult ::= SEQUENCE
    {
    }
    -- ================================================================================

    -- ================================================================================
    -- Message Control-msgs-Types/PidState
    -- ================================================================================
    -- Header header
    -- duration timestep
    -- float64 error
    -- float64 error_dot
    -- float64 p_error
    -- float64 i_error
    -- float64 d_error
    -- float64 p_term
    -- float64 i_term
    -- float64 d_term
    -- float64 i_max
    -- float64 i_min
    -- float64 output
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Control-msgs-Types/PidState
    Control-msgs-PidState ::= SEQUENCE
    {
        header Std-msgs-Header,
        timestep T-Time,
        error-value T-Double,
        error-dot T-Double,
        p-error T-Double,
        i-error T-Double,
        d-error T-Double,
        p-term T-Double,
        i-term T-Double,
        d-term T-Double,
        i-max T-Double,
        i-min T-Double,
        output-value T-Double
    }
    -- ================================================================================

    -- ================================================================================
    -- Message Control-msgs-Types/PointHeadAction
    -- ================================================================================
    -- # ====== DO NOT MODIFY! AUTOGENERATED FROM AN ACTION DEFINITION ======
    -- 
    -- PointHeadActionGoal action_goal
    -- PointHeadActionResult action_result
    -- PointHeadActionFeedback action_feedback
    -- 
    -- ================================================================================
    -- MSG: control_msgs/PointHeadActionGoal
    -- # ====== DO NOT MODIFY! AUTOGENERATED FROM AN ACTION DEFINITION ======
    -- 
    -- Header header
    -- actionlib_msgs/GoalID goal_id
    -- PointHeadGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/PointHeadGoal
    -- # ====== DO NOT MODIFY! AUTOGENERATED FROM AN ACTION DEFINITION ======
    -- geometry_msgs/PointStamped target
    -- geometry_msgs/Vector3 pointing_axis
    -- string pointing_frame
    -- duration min_duration
    -- float64 max_velocity
    -- 
    -- ================================================================================
    -- MSG: geometry_msgs/PointStamped
    -- # This represents a Point with reference coordinate frame and timestamp
    -- Header header
    -- Point point
    -- 
    -- ================================================================================
    -- MSG: geometry_msgs/Point
    -- # This contains the position of a point in free space
    -- float64 x
    -- float64 y
    -- float64 z
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: control_msgs/PointHeadActionResult
    -- # ====== DO NOT MODIFY! AUTOGENERATED FROM AN ACTION DEFINITION ======
    -- 
    -- Header header
    -- actionlib_msgs/GoalStatus status
    -- PointHeadResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: control_msgs/PointHeadResult
    -- # ====== DO NOT MODIFY! AUTOGENERATED FROM AN ACTION DEFINITION ======
    -- 
    -- ================================================================================
    -- MSG: control_msgs/PointHeadActionFeedback
    -- # ====== DO NOT MODIFY! AUTOGENERATED FROM AN ACTION DEFINITION ======
    -- 
    -- Header header
    -- actionlib_msgs/GoalStatus status
    -- PointHeadFeedback feedback
    -- 
    -- ================================================================================
    -- MSG: control_msgs/PointHeadFeedback
    -- # ====== DO NOT MODIFY! AUTOGENERATED FROM AN ACTION DEFINITION ======
    -- float64 pointing_angle_error
    -- 
    -- ================================================================================
    -- ASN.1 type for Control-msgs-Types/PointHeadAction
    Control-msgs-PointHeadAction ::= SEQUENCE
    {
        action-goal Control-msgs-PointHeadActionGoal,
        action-result Control-msgs-PointHeadActionResult,
        action-feedback Control-msgs-PointHeadActionFeedback
    }
    -- ================================================================================

    -- ================================================================================
    -- Message Control-msgs-Types/PointHeadActionFeedback
    -- ================================================================================
    -- # ====== DO NOT MODIFY! AUTOGENERATED FROM AN ACTION DEFINITION ======
    -- 
    -- Header header
    -- actionlib_msgs/GoalStatus status
    -- PointHeadFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/PointHeadFeedback
    -- # ====== DO NOT MODIFY! AUTOGENERATED FROM AN ACTION DEFINITION ======
    -- float64 pointing_angle_error
    -- 
    -- ================================================================================
    -- ASN.1 type for Control-msgs-Types/PointHeadActionFeedback
    Control-msgs-PointHeadActionFeedback ::= SEQUENCE
    {
        header Std-msgs-Header,
        status Actionlib-msgs-GoalStatus,
        feedback Control-msgs-PointHeadFeedback
    }
    -- ================================================================================

    -- ================================================================================
    -- Message Control-msgs-Types/PointHeadActionGoal
    -- ================================================================================
    -- # ====== DO NOT MODIFY! AUTOGENERATED FROM AN ACTION DEFINITION ======
    -- 
    -- Header header
    -- actionlib_msgs/GoalID goal_id
    -- PointHeadGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/PointHeadGoal
    -- # ====== DO NOT MODIFY! AUTOGENERATED FROM AN ACTION DEFINITION ======
    -- geometry_msgs/PointStamped target
    -- geometry_msgs/Vector3 pointing_axis
    -- string pointing_frame
    -- duration min_duration
    -- float64 max_velocity
    -- 
    -- ================================================================================
    -- MSG: geometry_msgs/PointStamped
    -- # This represents a Point with reference coordinate frame and timestamp
    -- Header header
    -- Point point
    -- 
    -- ================================================================================
    -- MSG: geometry_msgs/Point
    -- # This contains the position of a point in free space
    -- float64 x
    -- float64 y
    -- float64 z
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z    -- ================================================================================
    -- ASN.1 type for Control-msgs-Types/PointHeadActionGoal
    Control-msgs-PointHeadActionGoal ::= SEQUENCE
    {
        header Std-msgs-Header,
        goal-id Actionlib-msgs-GoalID,
        goal Control-msgs-PointHeadGoal
    }
    -- ================================================================================

    -- ================================================================================
    -- Message Control-msgs-Types/PointHeadActionResult
    -- ================================================================================
    -- # ====== DO NOT MODIFY! AUTOGENERATED FROM AN ACTION DEFINITION ======
    -- 
    -- Header header
    -- actionlib_msgs/GoalStatus status
    -- PointHeadResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/PointHeadResult
    -- # ====== DO NOT MODIFY! AUTOGENERATED FROM AN ACTION DEFINITION ======
    -- ================================================================================
    -- ASN.1 type for Control-msgs-Types/PointHeadActionResult
    Control-msgs-PointHeadActionResult ::= SEQUENCE
    {
        header Std-msgs-Header,
        status Actionlib-msgs-GoalStatus,
        result Control-msgs-PointHeadResult
    }
    -- ================================================================================

    -- ================================================================================
    -- Message Control-msgs-Types/PointHeadFeedback
    -- ================================================================================
    -- # ====== DO NOT MODIFY! AUTOGENERATED FROM AN ACTION DEFINITION ======
    -- float64 pointing_angle_error
    -- 
    -- ================================================================================
    -- ASN.1 type for Control-msgs-Types/PointHeadFeedback
    Control-msgs-PointHeadFeedback ::= T-Double

    -- ================================================================================

    -- ================================================================================
    -- Message Control-msgs-Types/PointHeadGoal
    -- ================================================================================
    -- # ====== DO NOT MODIFY! AUTOGENERATED FROM AN ACTION DEFINITION ======
    -- geometry_msgs/PointStamped target
    -- geometry_msgs/Vector3 pointing_axis
    -- string pointing_frame
    -- duration min_duration
    -- float64 max_velocity
    -- 
    -- ================================================================================
    -- MSG: geometry_msgs/PointStamped
    -- # This represents a Point with reference coordinate frame and timestamp
    -- Header header
    -- Point point
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Point
    -- # This contains the position of a point in free space
    -- float64 x
    -- float64 y
    -- float64 z
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z    -- ================================================================================
    -- ASN.1 type for Control-msgs-Types/PointHeadGoal
    Control-msgs-PointHeadGoal ::= SEQUENCE
    {
        target Geometry-msgs-PointStamped,
        pointing-axis Geometry-msgs-Vector3,
        pointing-frame T-String,
        min-duration T-Time,
        max-velocity T-Double
    }
    -- ================================================================================

    -- ================================================================================
    -- Message Control-msgs-Types/PointHeadResult
    -- ================================================================================
    -- # ====== DO NOT MODIFY! AUTOGENERATED FROM AN ACTION DEFINITION ======
    -- ================================================================================
    -- ASN.1 type for Control-msgs-Types/PointHeadResult
    Control-msgs-PointHeadResult ::= SEQUENCE
    {
    }
    -- ================================================================================

    -- ================================================================================
    -- Message Control-msgs-Types/SingleJointPositionAction
    -- ================================================================================
    -- # ====== DO NOT MODIFY! AUTOGENERATED FROM AN ACTION DEFINITION ======
    -- 
    -- SingleJointPositionActionGoal action_goal
    -- SingleJointPositionActionResult action_result
    -- SingleJointPositionActionFeedback action_feedback
    -- 
    -- ================================================================================
    -- MSG: control_msgs/SingleJointPositionActionGoal
    -- # ====== DO NOT MODIFY! AUTOGENERATED FROM AN ACTION DEFINITION ======
    -- 
    -- Header header
    -- actionlib_msgs/GoalID goal_id
    -- SingleJointPositionGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/SingleJointPositionGoal
    -- # ====== DO NOT MODIFY! AUTOGENERATED FROM AN ACTION DEFINITION ======
    -- float64 position
    -- duration min_duration
    -- float64 max_velocity
    -- 
    -- ================================================================================
    -- MSG: control_msgs/SingleJointPositionActionResult
    -- # ====== DO NOT MODIFY! AUTOGENERATED FROM AN ACTION DEFINITION ======
    -- 
    -- Header header
    -- actionlib_msgs/GoalStatus status
    -- SingleJointPositionResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: control_msgs/SingleJointPositionResult
    -- # ====== DO NOT MODIFY! AUTOGENERATED FROM AN ACTION DEFINITION ======
    -- 
    -- ================================================================================
    -- MSG: control_msgs/SingleJointPositionActionFeedback
    -- # ====== DO NOT MODIFY! AUTOGENERATED FROM AN ACTION DEFINITION ======
    -- 
    -- Header header
    -- actionlib_msgs/GoalStatus status
    -- SingleJointPositionFeedback feedback
    -- 
    -- ================================================================================
    -- MSG: control_msgs/SingleJointPositionFeedback
    -- # ====== DO NOT MODIFY! AUTOGENERATED FROM AN ACTION DEFINITION ======
    -- Header header
    -- float64 position
    -- float64 velocity
    -- float64 error
    -- 
    -- ================================================================================
    -- ASN.1 type for Control-msgs-Types/SingleJointPositionAction
    Control-msgs-SingleJointPositionAction ::= SEQUENCE
    {
        action-goal Control-msgs-SingleJointPositionActionGoal,
        action-result Control-msgs-SingleJointPositionActionResult,
        action-feedback Control-msgs-SingleJointPositionActionFeedback
    }
    -- ================================================================================

    -- ================================================================================
    -- Message Control-msgs-Types/SingleJointPositionActionFeedback
    -- ================================================================================
    -- # ====== DO NOT MODIFY! AUTOGENERATED FROM AN ACTION DEFINITION ======
    -- 
    -- Header header
    -- actionlib_msgs/GoalStatus status
    -- SingleJointPositionFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/SingleJointPositionFeedback
    -- # ====== DO NOT MODIFY! AUTOGENERATED FROM AN ACTION DEFINITION ======
    -- Header header
    -- float64 position
    -- float64 velocity
    -- float64 error
    -- 
    -- ================================================================================
    -- ASN.1 type for Control-msgs-Types/SingleJointPositionActionFeedback
    Control-msgs-SingleJointPositionActionFeedback ::= SEQUENCE
    {
        header Std-msgs-Header,
        status Actionlib-msgs-GoalStatus,
        feedback Control-msgs-SingleJointPositionFeedback
    }
    -- ================================================================================

    -- ================================================================================
    -- Message Control-msgs-Types/SingleJointPositionActionGoal
    -- ================================================================================
    -- # ====== DO NOT MODIFY! AUTOGENERATED FROM AN ACTION DEFINITION ======
    -- 
    -- Header header
    -- actionlib_msgs/GoalID goal_id
    -- SingleJointPositionGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/SingleJointPositionGoal
    -- # ====== DO NOT MODIFY! AUTOGENERATED FROM AN ACTION DEFINITION ======
    -- float64 position
    -- duration min_duration
    -- float64 max_velocity
    -- ================================================================================
    -- ASN.1 type for Control-msgs-Types/SingleJointPositionActionGoal
    Control-msgs-SingleJointPositionActionGoal ::= SEQUENCE
    {
        header Std-msgs-Header,
        goal-id Actionlib-msgs-GoalID,
        goal Control-msgs-SingleJointPositionGoal
    }
    -- ================================================================================

    -- ================================================================================
    -- Message Control-msgs-Types/SingleJointPositionActionResult
    -- ================================================================================
    -- # ====== DO NOT MODIFY! AUTOGENERATED FROM AN ACTION DEFINITION ======
    -- 
    -- Header header
    -- actionlib_msgs/GoalStatus status
    -- SingleJointPositionResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: control_msgs/SingleJointPositionResult
    -- # ====== DO NOT MODIFY! AUTOGENERATED FROM AN ACTION DEFINITION ======
    -- ================================================================================
    -- ASN.1 type for Control-msgs-Types/SingleJointPositionActionResult
    Control-msgs-SingleJointPositionActionResult ::= SEQUENCE
    {
        header Std-msgs-Header,
        status Actionlib-msgs-GoalStatus,
        result Control-msgs-SingleJointPositionResult
    }
    -- ================================================================================

    -- ================================================================================
    -- Message Control-msgs-Types/SingleJointPositionFeedback
    -- ================================================================================
    -- # ====== DO NOT MODIFY! AUTOGENERATED FROM AN ACTION DEFINITION ======
    -- Header header
    -- float64 position
    -- float64 velocity
    -- float64 error
    -- 
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Control-msgs-Types/SingleJointPositionFeedback
    Control-msgs-SingleJointPositionFeedback ::= SEQUENCE
    {
        header Std-msgs-Header,
        position T-Double,
        velocity T-Double,
        error-value T-Double
    }
    -- ================================================================================

    -- ================================================================================
    -- Message Control-msgs-Types/SingleJointPositionGoal
    -- ================================================================================
    -- # ====== DO NOT MODIFY! AUTOGENERATED FROM AN ACTION DEFINITION ======
    -- float64 position
    -- duration min_duration
    -- float64 max_velocity
    -- ================================================================================
    -- ASN.1 type for Control-msgs-Types/SingleJointPositionGoal
    Control-msgs-SingleJointPositionGoal ::= SEQUENCE
    {
        position T-Double,
        min-duration T-Time,
        max-velocity T-Double
    }
    -- ================================================================================

    -- ================================================================================
    -- Message Control-msgs-Types/SingleJointPositionResult
    -- ================================================================================
    -- # ====== DO NOT MODIFY! AUTOGENERATED FROM AN ACTION DEFINITION ======
    -- ================================================================================
    -- ASN.1 type for Control-msgs-Types/SingleJointPositionResult
    Control-msgs-SingleJointPositionResult ::= SEQUENCE
    {
    }
    -- ================================================================================

END
