-- Generated from userdefs.asn.mako for package smach_msgs

UserDefs-Smach-msgs-Types DEFINITIONS ::=
BEGIN

IMPORTS T-UInt32 FROM TASTE-BasicTypes;

    -- Dummy type (TASTE doesn't handle the includes correctly if an ASN.1 file defines only constants)
    Dummy-Smach-msgs-Types-T ::= T-UInt32

    -- Size constants definitions: to be set according to the application's needs

    -- Size constant for type Smach-msgs-SmachContainerStatus
    max-Smach-msgs-SmachContainerStatus T-UInt32 ::= 60

    -- Size constant for type Smach-msgs-SmachContainerInitialStatusCmd
    max-Smach-msgs-SmachContainerInitialStatusCmd T-UInt32 ::= 60

    -- Size constant for type Smach-msgs-SmachContainerStructure
    max-Smach-msgs-SmachContainerStructure T-UInt32 ::= 60

END
