-- Generated from package.asn.mako for package tf2_msgs

Tf2-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-TransformStamped FROM Geometry-msgs-Types
Actionlib-msgs-GoalID, Actionlib-msgs-GoalStatus FROM Actionlib-msgs-Types
Std-msgs-Header FROM Std-msgs-Types
max-Tf2-msgs-TFMessage, Dummy-Tf2-msgs-Types-T FROM UserDefs-Tf2-msgs-Types;
    -- ================================================================================
    -- Message Tf2-msgs-Types/LookupTransformAction
    -- ================================================================================
    -- # ====== DO NOT MODIFY! AUTOGENERATED FROM AN ACTION DEFINITION ======
    -- 
    -- LookupTransformActionGoal action_goal
    -- LookupTransformActionResult action_result
    -- LookupTransformActionFeedback action_feedback
    -- 
    -- ================================================================================
    -- MSG: tf2_msgs/LookupTransformActionGoal
    -- # ====== DO NOT MODIFY! AUTOGENERATED FROM AN ACTION DEFINITION ======
    -- 
    -- Header header
    -- actionlib_msgs/GoalID goal_id
    -- LookupTransformGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: tf2_msgs/LookupTransformGoal
    -- # ====== DO NOT MODIFY! AUTOGENERATED FROM AN ACTION DEFINITION ======
    -- #Simple API
    -- string target_frame
    -- string source_frame
    -- time source_time
    -- duration timeout
    -- 
    -- #Advanced API
    -- time target_time
    -- string fixed_frame
    -- 
    -- #Whether or not to use the advanced API
    -- bool advanced
    -- 
    -- 
    -- ================================================================================
    -- MSG: tf2_msgs/LookupTransformActionResult
    -- # ====== DO NOT MODIFY! AUTOGENERATED FROM AN ACTION DEFINITION ======
    -- 
    -- Header header
    -- actionlib_msgs/GoalStatus status
    -- LookupTransformResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: tf2_msgs/LookupTransformResult
    -- # ====== DO NOT MODIFY! AUTOGENERATED FROM AN ACTION DEFINITION ======
    -- geometry_msgs/TransformStamped transform
    -- tf2_msgs/TF2Error error
    -- 
    -- ================================================================================
    -- MSG: geometry_msgs/TransformStamped
    -- # This expresses a transform from coordinate frame header.frame_id
    -- # to the coordinate frame child_frame_id
    -- #
    -- # This message is mostly used by the 
    -- # <a href="http://wiki.ros.org/tf">tf</a> package. 
    -- # See its documentation for more information.
    -- 
    -- Header header
    -- string child_frame_id # the frame id of the child frame
    -- Transform transform
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- 
    -- ================================================================================
    -- MSG: tf2_msgs/TF2Error
    -- uint8 NO_ERROR = 0
    -- uint8 LOOKUP_ERROR = 1
    -- uint8 CONNECTIVITY_ERROR = 2
    -- uint8 EXTRAPOLATION_ERROR = 3
    -- uint8 INVALID_ARGUMENT_ERROR = 4
    -- uint8 TIMEOUT_ERROR = 5
    -- uint8 TRANSFORM_ERROR = 6
    -- 
    -- uint8 error
    -- string error_string
    -- 
    -- ================================================================================
    -- MSG: tf2_msgs/LookupTransformActionFeedback
    -- # ====== DO NOT MODIFY! AUTOGENERATED FROM AN ACTION DEFINITION ======
    -- 
    -- Header header
    -- actionlib_msgs/GoalStatus status
    -- LookupTransformFeedback feedback
    -- 
    -- ================================================================================
    -- MSG: tf2_msgs/LookupTransformFeedback
    -- # ====== DO NOT MODIFY! AUTOGENERATED FROM AN ACTION DEFINITION ======
    -- 
    -- ================================================================================
    -- ASN.1 type for Tf2-msgs-Types/LookupTransformAction
    Tf2-msgs-LookupTransformAction ::= SEQUENCE
    {
        action-goal Tf2-msgs-LookupTransformActionGoal,
        action-result Tf2-msgs-LookupTransformActionResult,
        action-feedback Tf2-msgs-LookupTransformActionFeedback
    }
    -- ================================================================================

    -- ================================================================================
    -- Message Tf2-msgs-Types/LookupTransformActionFeedback
    -- ================================================================================
    -- # ====== DO NOT MODIFY! AUTOGENERATED FROM AN ACTION DEFINITION ======
    -- 
    -- Header header
    -- actionlib_msgs/GoalStatus status
    -- LookupTransformFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: tf2_msgs/LookupTransformFeedback
    -- # ====== DO NOT MODIFY! AUTOGENERATED FROM AN ACTION DEFINITION ======
    -- 
    -- ================================================================================
    -- ASN.1 type for Tf2-msgs-Types/LookupTransformActionFeedback
    Tf2-msgs-LookupTransformActionFeedback ::= SEQUENCE
    {
        header Std-msgs-Header,
        status Actionlib-msgs-GoalStatus,
        feedback Tf2-msgs-LookupTransformFeedback
    }
    -- ================================================================================

    -- ================================================================================
    -- Message Tf2-msgs-Types/LookupTransformActionGoal
    -- ================================================================================
    -- # ====== DO NOT MODIFY! AUTOGENERATED FROM AN ACTION DEFINITION ======
    -- 
    -- Header header
    -- actionlib_msgs/GoalID goal_id
    -- LookupTransformGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: tf2_msgs/LookupTransformGoal
    -- # ====== DO NOT MODIFY! AUTOGENERATED FROM AN ACTION DEFINITION ======
    -- #Simple API
    -- string target_frame
    -- string source_frame
    -- time source_time
    -- duration timeout
    -- 
    -- #Advanced API
    -- time target_time
    -- string fixed_frame
    -- 
    -- #Whether or not to use the advanced API
    -- bool advanced
    -- 
    -- ================================================================================
    -- ASN.1 type for Tf2-msgs-Types/LookupTransformActionGoal
    Tf2-msgs-LookupTransformActionGoal ::= SEQUENCE
    {
        header Std-msgs-Header,
        goal-id Actionlib-msgs-GoalID,
        goal Tf2-msgs-LookupTransformGoal
    }
    -- ================================================================================

    -- ================================================================================
    -- Message Tf2-msgs-Types/LookupTransformActionResult
    -- ================================================================================
    -- # ====== DO NOT MODIFY! AUTOGENERATED FROM AN ACTION DEFINITION ======
    -- 
    -- Header header
    -- actionlib_msgs/GoalStatus status
    -- LookupTransformResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: tf2_msgs/LookupTransformResult
    -- # ====== DO NOT MODIFY! AUTOGENERATED FROM AN ACTION DEFINITION ======
    -- geometry_msgs/TransformStamped transform
    -- tf2_msgs/TF2Error error
    -- 
    -- ================================================================================
    -- MSG: geometry_msgs/TransformStamped
    -- # This expresses a transform from coordinate frame header.frame_id
    -- # to the coordinate frame child_frame_id
    -- #
    -- # This message is mostly used by the 
    -- # <a href="http://wiki.ros.org/tf">tf</a> package. 
    -- # See its documentation for more information.
    -- 
    -- Header header
    -- string child_frame_id # the frame id of the child frame
    -- Transform transform
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- 
    -- ================================================================================
    -- MSG: tf2_msgs/TF2Error
    -- uint8 NO_ERROR = 0
    -- uint8 LOOKUP_ERROR = 1
    -- uint8 CONNECTIVITY_ERROR = 2
    -- uint8 EXTRAPOLATION_ERROR = 3
    -- uint8 INVALID_ARGUMENT_ERROR = 4
    -- uint8 TIMEOUT_ERROR = 5
    -- uint8 TRANSFORM_ERROR = 6
    -- 
    -- uint8 error
    -- string error_string
    -- ================================================================================
    -- ASN.1 type for Tf2-msgs-Types/LookupTransformActionResult
    Tf2-msgs-LookupTransformActionResult ::= SEQUENCE
    {
        header Std-msgs-Header,
        status Actionlib-msgs-GoalStatus,
        result Tf2-msgs-LookupTransformResult
    }
    -- ================================================================================

    -- ================================================================================
    -- Message Tf2-msgs-Types/LookupTransformFeedback
    -- ================================================================================
    -- # ====== DO NOT MODIFY! AUTOGENERATED FROM AN ACTION DEFINITION ======
    -- 
    -- ================================================================================
    -- ASN.1 type for Tf2-msgs-Types/LookupTransformFeedback
    Tf2-msgs-LookupTransformFeedback ::= SEQUENCE
    {
    }
    -- ================================================================================

    -- ================================================================================
    -- Message Tf2-msgs-Types/LookupTransformGoal
    -- ================================================================================
    -- # ====== DO NOT MODIFY! AUTOGENERATED FROM AN ACTION DEFINITION ======
    -- #Simple API
    -- string target_frame
    -- string source_frame
    -- time source_time
    -- duration timeout
    -- 
    -- #Advanced API
    -- time target_time
    -- string fixed_frame
    -- 
    -- #Whether or not to use the advanced API
    -- bool advanced
    -- 
    -- ================================================================================
    -- ASN.1 type for Tf2-msgs-Types/LookupTransformGoal
    Tf2-msgs-LookupTransformGoal ::= SEQUENCE
    {
        target-frame T-String,
        source-frame T-String,
        source-time T-Time,
        timeout T-Time,
        target-time T-Time,
        fixed-frame T-String,
        advanced T-Boolean
    }
    -- ================================================================================

    -- ================================================================================
    -- Message Tf2-msgs-Types/LookupTransformResult
    -- ================================================================================
    -- # ====== DO NOT MODIFY! AUTOGENERATED FROM AN ACTION DEFINITION ======
    -- geometry_msgs/TransformStamped transform
    -- tf2_msgs/TF2Error error
    -- 
    -- ================================================================================
    -- MSG: geometry_msgs/TransformStamped
    -- # This expresses a transform from coordinate frame header.frame_id
    -- # to the coordinate frame child_frame_id
    -- #
    -- # This message is mostly used by the 
    -- # <a href="http://wiki.ros.org/tf">tf</a> package. 
    -- # See its documentation for more information.
    -- 
    -- Header header
    -- string child_frame_id # the frame id of the child frame
    -- Transform transform
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- 
    -- ================================================================================
    -- MSG: tf2_msgs/TF2Error
    -- uint8 NO_ERROR = 0
    -- uint8 LOOKUP_ERROR = 1
    -- uint8 CONNECTIVITY_ERROR = 2
    -- uint8 EXTRAPOLATION_ERROR = 3
    -- uint8 INVALID_ARGUMENT_ERROR = 4
    -- uint8 TIMEOUT_ERROR = 5
    -- uint8 TRANSFORM_ERROR = 6
    -- 
    -- uint8 error
    -- string error_string
    -- ================================================================================
    -- ASN.1 type for Tf2-msgs-Types/LookupTransformResult
    Tf2-msgs-LookupTransformResult ::= SEQUENCE
    {
        transform Geometry-msgs-TransformStamped,
        error-value Tf2-msgs-TF2Error
    }
    -- ================================================================================

    -- ================================================================================
    -- Message Tf2-msgs-Types/TF2Error
    -- ================================================================================
    -- uint8 NO_ERROR = 0
    -- uint8 LOOKUP_ERROR = 1
    -- uint8 CONNECTIVITY_ERROR = 2
    -- uint8 EXTRAPOLATION_ERROR = 3
    -- uint8 INVALID_ARGUMENT_ERROR = 4
    -- uint8 TIMEOUT_ERROR = 5
    -- uint8 TRANSFORM_ERROR = 6
    -- 
    -- uint8 error
    -- string error_string
    -- ================================================================================
    -- ASN.1 type for Tf2-msgs-Types/TF2Error
    Tf2-msgs-TF2Error ::= SEQUENCE
    {
        error-value T-UInt8,
        error-string T-String
    }
    -- ================================================================================

    -- ================================================================================
    -- Message Tf2-msgs-Types/TFMessage
    -- ================================================================================
    -- geometry_msgs/TransformStamped[] transforms
    -- 
    -- ================================================================================
    -- MSG: geometry_msgs/TransformStamped
    -- # This expresses a transform from coordinate frame header.frame_id
    -- # to the coordinate frame child_frame_id
    -- #
    -- # This message is mostly used by the 
    -- # <a href="http://wiki.ros.org/tf">tf</a> package. 
    -- # See its documentation for more information.
    -- 
    -- Header header
    -- string child_frame_id # the frame id of the child frame
    -- Transform transform
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- ================================================================================
    -- ASN.1 type for Tf2-msgs-Types/TFMessage
    Tf2-msgs-TFMessage ::= SEQUENCE (SIZE(0..max-Tf2-msgs-TFMessage)) OF Geometry-msgs-TransformStamped
    -- ================================================================================

END
