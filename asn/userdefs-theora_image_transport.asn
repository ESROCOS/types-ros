-- Generated from userdefs.asn.mako for package theora_image_transport

UserDefs-Theora-image-transport-Types DEFINITIONS ::=
BEGIN

IMPORTS T-UInt32 FROM TASTE-BasicTypes;

    -- Dummy type (TASTE doesn't handle the includes correctly if an ASN.1 file defines only constants)
    Dummy-Theora-image-transport-Types-T ::= T-UInt32

    -- Size constants definitions: to be set according to the application's needs

    -- Size constant for type Theora-image-transport-Packet
    max-Theora-image-transport-Packet T-UInt32 ::= 60

END
