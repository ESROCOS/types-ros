-- Generated from package.asn.mako for package rospy_tutorials

Rospy-tutorials-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Std-msgs-Header FROM Std-msgs-Types
max-Rospy-tutorials-Floats, Dummy-Rospy-tutorials-Types-T FROM UserDefs-Rospy-tutorials-Types;
    -- ================================================================================
    -- Message Rospy-tutorials-Types/Floats
    -- ================================================================================
    -- float32[] data
    -- ================================================================================
    -- ASN.1 type for Rospy-tutorials-Types/Floats
    Rospy-tutorials-Floats ::= SEQUENCE (SIZE(0..max-Rospy-tutorials-Floats)) OF T-Float
    -- ================================================================================

    -- ================================================================================
    -- Message Rospy-tutorials-Types/HeaderString
    -- ================================================================================
    -- Header header
    -- string data
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Rospy-tutorials-Types/HeaderString
    Rospy-tutorials-HeaderString ::= SEQUENCE
    {
        header Std-msgs-Header,
        data-value T-String
    }
    -- ================================================================================

END
