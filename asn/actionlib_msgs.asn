-- Generated from package.asn.mako for package actionlib_msgs

Actionlib-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Std-msgs-Header FROM Std-msgs-Types
max-Actionlib-msgs-GoalStatusArray, Dummy-Actionlib-msgs-Types-T FROM UserDefs-Actionlib-msgs-Types;
    -- ================================================================================
    -- Message Actionlib-msgs-Types/GoalID
    -- ================================================================================
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- ================================================================================
    -- ASN.1 type for Actionlib-msgs-Types/GoalID
    Actionlib-msgs-GoalID ::= SEQUENCE
    {
        stamp T-Time,
        id T-String
    }
    -- ================================================================================

    -- ================================================================================
    -- Message Actionlib-msgs-Types/GoalStatus
    -- ================================================================================
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- ================================================================================
    -- ASN.1 type for Actionlib-msgs-Types/GoalStatus
    Actionlib-msgs-GoalStatus ::= SEQUENCE
    {
        goal-id Actionlib-msgs-GoalID,
        status T-UInt8,
        text T-String
    }
    -- ================================================================================

    -- ================================================================================
    -- Message Actionlib-msgs-Types/GoalStatusArray
    -- ================================================================================
    -- # Stores the statuses for goals that are currently being tracked
    -- # by an action server
    -- Header header
    -- GoalStatus[] status_list
    -- 
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- ================================================================================
    -- ASN.1 type for Actionlib-msgs-Types/GoalStatusArray
    Actionlib-msgs-GoalStatusArray ::= SEQUENCE
    {
        header Std-msgs-Header,
        status-list SEQUENCE (SIZE(0..max-Actionlib-msgs-GoalStatusArray)) OF Actionlib-msgs-GoalStatus
    }
    -- ================================================================================

END
