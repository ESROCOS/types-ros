-- Generated from package.asn.mako for package nav_msgs

Nav-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-Pose, Geometry-msgs-PoseStamped, Geometry-msgs-TwistWithCovariance, Geometry-msgs-PoseWithCovariance, Geometry-msgs-Point FROM Geometry-msgs-Types
Actionlib-msgs-GoalID, Actionlib-msgs-GoalStatus FROM Actionlib-msgs-Types
Std-msgs-Header FROM Std-msgs-Types
max-Nav-msgs-Path, max-Nav-msgs-OccupancyGrid, max-Nav-msgs-GridCells, Dummy-Nav-msgs-Types-T FROM UserDefs-Nav-msgs-Types;
    -- ================================================================================
    -- Message Nav-msgs-Types/GetMapAction
    -- ================================================================================
    -- # ====== DO NOT MODIFY! AUTOGENERATED FROM AN ACTION DEFINITION ======
    -- 
    -- GetMapActionGoal action_goal
    -- GetMapActionResult action_result
    -- GetMapActionFeedback action_feedback
    -- 
    -- ================================================================================
    -- MSG: nav_msgs/GetMapActionGoal
    -- # ====== DO NOT MODIFY! AUTOGENERATED FROM AN ACTION DEFINITION ======
    -- 
    -- Header header
    -- actionlib_msgs/GoalID goal_id
    -- GetMapGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: nav_msgs/GetMapGoal
    -- # ====== DO NOT MODIFY! AUTOGENERATED FROM AN ACTION DEFINITION ======
    -- # Get the map as a nav_msgs/OccupancyGrid
    -- 
    -- ================================================================================
    -- MSG: nav_msgs/GetMapActionResult
    -- # ====== DO NOT MODIFY! AUTOGENERATED FROM AN ACTION DEFINITION ======
    -- 
    -- Header header
    -- actionlib_msgs/GoalStatus status
    -- GetMapResult result
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: nav_msgs/GetMapResult
    -- # ====== DO NOT MODIFY! AUTOGENERATED FROM AN ACTION DEFINITION ======
    -- nav_msgs/OccupancyGrid map
    -- 
    -- ================================================================================
    -- MSG: nav_msgs/OccupancyGrid
    -- # This represents a 2-D grid map, in which each cell represents the probability of
    -- # occupancy.
    -- 
    -- Header header 
    -- 
    -- #MetaData for the map
    -- MapMetaData info
    -- 
    -- # The map data, in row-major order, starting with (0,0).  Occupancy
    -- # probabilities are in the range [0,100].  Unknown is -1.
    -- int8[] data
    -- 
    -- ================================================================================
    -- MSG: nav_msgs/MapMetaData
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: nav_msgs/GetMapActionFeedback
    -- # ====== DO NOT MODIFY! AUTOGENERATED FROM AN ACTION DEFINITION ======
    -- 
    -- Header header
    -- actionlib_msgs/GoalStatus status
    -- GetMapFeedback feedback
    -- 
    -- ================================================================================
    -- MSG: nav_msgs/GetMapFeedback
    -- # ====== DO NOT MODIFY! AUTOGENERATED FROM AN ACTION DEFINITION ======
    -- # no feedback
    -- ================================================================================
    -- ASN.1 type for Nav-msgs-Types/GetMapAction
    Nav-msgs-GetMapAction ::= SEQUENCE
    {
        action-goal Nav-msgs-GetMapActionGoal,
        action-result Nav-msgs-GetMapActionResult,
        action-feedback Nav-msgs-GetMapActionFeedback
    }
    -- ================================================================================

    -- ================================================================================
    -- Message Nav-msgs-Types/GetMapActionFeedback
    -- ================================================================================
    -- # ====== DO NOT MODIFY! AUTOGENERATED FROM AN ACTION DEFINITION ======
    -- 
    -- Header header
    -- actionlib_msgs/GoalStatus status
    -- GetMapFeedback feedback
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: nav_msgs/GetMapFeedback
    -- # ====== DO NOT MODIFY! AUTOGENERATED FROM AN ACTION DEFINITION ======
    -- # no feedback
    -- ================================================================================
    -- ASN.1 type for Nav-msgs-Types/GetMapActionFeedback
    Nav-msgs-GetMapActionFeedback ::= SEQUENCE
    {
        header Std-msgs-Header,
        status Actionlib-msgs-GoalStatus,
        feedback Nav-msgs-GetMapFeedback
    }
    -- ================================================================================

    -- ================================================================================
    -- Message Nav-msgs-Types/GetMapActionGoal
    -- ================================================================================
    -- # ====== DO NOT MODIFY! AUTOGENERATED FROM AN ACTION DEFINITION ======
    -- 
    -- Header header
    -- actionlib_msgs/GoalID goal_id
    -- GetMapGoal goal
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: nav_msgs/GetMapGoal
    -- # ====== DO NOT MODIFY! AUTOGENERATED FROM AN ACTION DEFINITION ======
    -- # Get the map as a nav_msgs/OccupancyGrid
    -- ================================================================================
    -- ASN.1 type for Nav-msgs-Types/GetMapActionGoal
    Nav-msgs-GetMapActionGoal ::= SEQUENCE
    {
        header Std-msgs-Header,
        goal-id Actionlib-msgs-GoalID,
        goal Nav-msgs-GetMapGoal
    }
    -- ================================================================================

    -- ================================================================================
    -- Message Nav-msgs-Types/GetMapActionResult
    -- ================================================================================
    -- # ====== DO NOT MODIFY! AUTOGENERATED FROM AN ACTION DEFINITION ======
    -- 
    -- Header header
    -- actionlib_msgs/GoalStatus status
    -- GetMapResult result
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: actionlib_msgs/GoalStatus
    -- GoalID goal_id
    -- uint8 status
    -- uint8 PENDING         = 0   # The goal has yet to be processed by the action server
    -- uint8 ACTIVE          = 1   # The goal is currently being processed by the action server
    -- uint8 PREEMPTED       = 2   # The goal received a cancel request after it started executing
    --                             #   and has since completed its execution (Terminal State)
    -- uint8 SUCCEEDED       = 3   # The goal was achieved successfully by the action server (Terminal State)
    -- uint8 ABORTED         = 4   # The goal was aborted during execution by the action server due
    --                             #    to some failure (Terminal State)
    -- uint8 REJECTED        = 5   # The goal was rejected by the action server without being processed,
    --                             #    because the goal was unattainable or invalid (Terminal State)
    -- uint8 PREEMPTING      = 6   # The goal received a cancel request after it started executing
    --                             #    and has not yet completed execution
    -- uint8 RECALLING       = 7   # The goal received a cancel request before it started executing,
    --                             #    but the action server has not yet confirmed that the goal is canceled
    -- uint8 RECALLED        = 8   # The goal received a cancel request before it started executing
    --                             #    and was successfully cancelled (Terminal State)
    -- uint8 LOST            = 9   # An action client can determine that a goal is LOST. This should not be
    --                             #    sent over the wire by an action server
    -- 
    -- #Allow for the user to associate a string with GoalStatus for debugging
    -- string text
    -- 
    -- 
    -- ================================================================================
    -- MSG: actionlib_msgs/GoalID
    -- # The stamp should store the time at which this goal was requested.
    -- # It is used by an action server when it tries to preempt all
    -- # goals that were requested before a certain time
    -- time stamp
    -- 
    -- # The id provides a way to associate feedback and
    -- # result message with specific goal requests. The id
    -- # specified must be unique.
    -- string id
    -- 
    -- 
    -- ================================================================================
    -- MSG: nav_msgs/GetMapResult
    -- # ====== DO NOT MODIFY! AUTOGENERATED FROM AN ACTION DEFINITION ======
    -- nav_msgs/OccupancyGrid map
    -- 
    -- ================================================================================
    -- MSG: nav_msgs/OccupancyGrid
    -- # This represents a 2-D grid map, in which each cell represents the probability of
    -- # occupancy.
    -- 
    -- Header header 
    -- 
    -- #MetaData for the map
    -- MapMetaData info
    -- 
    -- # The map data, in row-major order, starting with (0,0).  Occupancy
    -- # probabilities are in the range [0,100].  Unknown is -1.
    -- int8[] data
    -- 
    -- ================================================================================
    -- MSG: nav_msgs/MapMetaData
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Nav-msgs-Types/GetMapActionResult
    Nav-msgs-GetMapActionResult ::= SEQUENCE
    {
        header Std-msgs-Header,
        status Actionlib-msgs-GoalStatus,
        result Nav-msgs-GetMapResult
    }
    -- ================================================================================

    -- ================================================================================
    -- Message Nav-msgs-Types/GetMapFeedback
    -- ================================================================================
    -- # ====== DO NOT MODIFY! AUTOGENERATED FROM AN ACTION DEFINITION ======
    -- # no feedback
    -- ================================================================================
    -- ASN.1 type for Nav-msgs-Types/GetMapFeedback
    Nav-msgs-GetMapFeedback ::= SEQUENCE
    {
    }
    -- ================================================================================

    -- ================================================================================
    -- Message Nav-msgs-Types/GetMapGoal
    -- ================================================================================
    -- # ====== DO NOT MODIFY! AUTOGENERATED FROM AN ACTION DEFINITION ======
    -- # Get the map as a nav_msgs/OccupancyGrid
    -- ================================================================================
    -- ASN.1 type for Nav-msgs-Types/GetMapGoal
    Nav-msgs-GetMapGoal ::= SEQUENCE
    {
    }
    -- ================================================================================

    -- ================================================================================
    -- Message Nav-msgs-Types/GetMapResult
    -- ================================================================================
    -- # ====== DO NOT MODIFY! AUTOGENERATED FROM AN ACTION DEFINITION ======
    -- nav_msgs/OccupancyGrid map
    -- 
    -- ================================================================================
    -- MSG: nav_msgs/OccupancyGrid
    -- # This represents a 2-D grid map, in which each cell represents the probability of
    -- # occupancy.
    -- 
    -- Header header 
    -- 
    -- #MetaData for the map
    -- MapMetaData info
    -- 
    -- # The map data, in row-major order, starting with (0,0).  Occupancy
    -- # probabilities are in the range [0,100].  Unknown is -1.
    -- int8[] data
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: nav_msgs/MapMetaData
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Nav-msgs-Types/GetMapResult
    Nav-msgs-GetMapResult ::= Nav-msgs-OccupancyGrid

    -- ================================================================================

    -- ================================================================================
    -- Message Nav-msgs-Types/GridCells
    -- ================================================================================
    -- #an array of cells in a 2D grid
    -- Header header
    -- float32 cell_width
    -- float32 cell_height
    -- geometry_msgs/Point[] cells
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Point
    -- # This contains the position of a point in free space
    -- float64 x
    -- float64 y
    -- float64 z
    -- ================================================================================
    -- ASN.1 type for Nav-msgs-Types/GridCells
    Nav-msgs-GridCells ::= SEQUENCE
    {
        header Std-msgs-Header,
        cell-width T-Float,
        cell-height T-Float,
        cells SEQUENCE (SIZE(0..max-Nav-msgs-GridCells)) OF Geometry-msgs-Point
    }
    -- ================================================================================

    -- ================================================================================
    -- Message Nav-msgs-Types/MapMetaData
    -- ================================================================================
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Nav-msgs-Types/MapMetaData
    Nav-msgs-MapMetaData ::= SEQUENCE
    {
        map-load-time T-Time,
        resolution T-Float,
        width T-UInt32,
        height T-UInt32,
        origin Geometry-msgs-Pose
    }
    -- ================================================================================

    -- ================================================================================
    -- Message Nav-msgs-Types/OccupancyGrid
    -- ================================================================================
    -- # This represents a 2-D grid map, in which each cell represents the probability of
    -- # occupancy.
    -- 
    -- Header header 
    -- 
    -- #MetaData for the map
    -- MapMetaData info
    -- 
    -- # The map data, in row-major order, starting with (0,0).  Occupancy
    -- # probabilities are in the range [0,100].  Unknown is -1.
    -- int8[] data
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: nav_msgs/MapMetaData
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Nav-msgs-Types/OccupancyGrid
    Nav-msgs-OccupancyGrid ::= SEQUENCE
    {
        header Std-msgs-Header,
        info Nav-msgs-MapMetaData,
        data-value SEQUENCE (SIZE(0..max-Nav-msgs-OccupancyGrid)) OF T-Int8
    }
    -- ================================================================================

    -- ================================================================================
    -- Message Nav-msgs-Types/Odometry
    -- ================================================================================
    -- # This represents an estimate of a position and velocity in free space.  
    -- # The pose in this message should be specified in the coordinate frame given by header.frame_id.
    -- # The twist in this message should be specified in the coordinate frame given by the child_frame_id
    -- Header header
    -- string child_frame_id
    -- geometry_msgs/PoseWithCovariance pose
    -- geometry_msgs/TwistWithCovariance twist
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/PoseWithCovariance
    -- # This represents a pose in free space with uncertainty.
    -- 
    -- Pose pose
    -- 
    -- # Row-major representation of the 6x6 covariance matrix
    -- # The orientation parameters use a fixed-axis representation.
    -- # In order, the parameters are:
    -- # (x, y, z, rotation about X axis, rotation about Y axis, rotation about Z axis)
    -- float64[36] covariance
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: geometry_msgs/TwistWithCovariance
    -- # This expresses velocity in free space with uncertainty.
    -- 
    -- Twist twist
    -- 
    -- # Row-major representation of the 6x6 covariance matrix
    -- # The orientation parameters use a fixed-axis representation.
    -- # In order, the parameters are:
    -- # (x, y, z, rotation about X axis, rotation about Y axis, rotation about Z axis)
    -- float64[36] covariance
    -- 
    -- ================================================================================
    -- MSG: geometry_msgs/Twist
    -- # This expresses velocity in free space broken into its linear and angular parts.
    -- Vector3  linear
    -- Vector3  angular
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z    -- ================================================================================
    -- ASN.1 type for Nav-msgs-Types/Odometry
    Nav-msgs-Odometry ::= SEQUENCE
    {
        header Std-msgs-Header,
        child-frame-id T-String,
        pose Geometry-msgs-PoseWithCovariance,
        twist Geometry-msgs-TwistWithCovariance
    }
    -- ================================================================================

    -- ================================================================================
    -- Message Nav-msgs-Types/Path
    -- ================================================================================
    -- #An array of poses that represents a Path for a robot to follow
    -- Header header
    -- geometry_msgs/PoseStamped[] poses
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/PoseStamped
    -- # A Pose with reference coordinate frame and timestamp
    -- Header header
    -- Pose pose
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Nav-msgs-Types/Path
    Nav-msgs-Path ::= SEQUENCE
    {
        header Std-msgs-Header,
        poses SEQUENCE (SIZE(0..max-Nav-msgs-Path)) OF Geometry-msgs-PoseStamped
    }
    -- ================================================================================

END
