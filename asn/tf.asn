-- Generated from package.asn.mako for package tf

Tf-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-TransformStamped FROM Geometry-msgs-Types
max-Tf-tfMessage, Dummy-Tf-Types-T FROM UserDefs-Tf-Types;
    -- ================================================================================
    -- Message Tf-Types/tfMessage
    -- ================================================================================
    -- geometry_msgs/TransformStamped[] transforms
    -- 
    -- ================================================================================
    -- MSG: geometry_msgs/TransformStamped
    -- # This expresses a transform from coordinate frame header.frame_id
    -- # to the coordinate frame child_frame_id
    -- #
    -- # This message is mostly used by the 
    -- # <a href="http://wiki.ros.org/tf">tf</a> package. 
    -- # See its documentation for more information.
    -- 
    -- Header header
    -- string child_frame_id # the frame id of the child frame
    -- Transform transform
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- ================================================================================
    -- ASN.1 type for Tf-Types/tfMessage
    Tf-tfMessage ::= SEQUENCE (SIZE(0..max-Tf-tfMessage)) OF Geometry-msgs-TransformStamped
    -- ================================================================================

END
