-- Generated from package.asn.mako for package visualization_msgs

Visualization-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-Quaternion, Geometry-msgs-Pose, Geometry-msgs-Vector3, Geometry-msgs-Point FROM Geometry-msgs-Types
Std-msgs-Header, Std-msgs-ColorRGBA FROM Std-msgs-Types
max-Visualization-msgs-InteractiveMarkerInit, max-Visualization-msgs-MarkerArray, max-Visualization-msgs-InteractiveMarkerControl, max-Visualization-msgs-InteractiveMarkerUpdate, max-Visualization-msgs-InteractiveMarker, max-Visualization-msgs-Marker, max-Visualization-msgs-ImageMarker, Dummy-Visualization-msgs-Types-T FROM UserDefs-Visualization-msgs-Types;
    -- ================================================================================
    -- Message Visualization-msgs-Types/ImageMarker
    -- ================================================================================
    -- uint8 CIRCLE=0
    -- uint8 LINE_STRIP=1
    -- uint8 LINE_LIST=2
    -- uint8 POLYGON=3
    -- uint8 POINTS=4
    -- 
    -- uint8 ADD=0
    -- uint8 REMOVE=1
    -- 
    -- Header header
    -- string ns		# namespace, used with id to form a unique id
    -- int32 id          	# unique id within the namespace
    -- int32 type        	# CIRCLE/LINE_STRIP/etc.
    -- int32 action      	# ADD/REMOVE
    -- geometry_msgs/Point position # 2D, in pixel-coords
    -- float32 scale	 	# the diameter for a circle, etc.
    -- std_msgs/ColorRGBA outline_color
    -- uint8 filled		# whether to fill in the shape with color
    -- std_msgs/ColorRGBA fill_color # color [0.0-1.0]
    -- duration lifetime       # How long the object should last before being automatically deleted.  0 means forever
    -- 
    -- 
    -- geometry_msgs/Point[] points # used for LINE_STRIP/LINE_LIST/POINTS/etc., 2D in pixel coords
    -- std_msgs/ColorRGBA[] outline_colors # a color for each line, point, etc.
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Point
    -- # This contains the position of a point in free space
    -- float64 x
    -- float64 y
    -- float64 z
    -- 
    -- ================================================================================
    -- MSG: std_msgs/ColorRGBA
    -- float32 r
    -- float32 g
    -- float32 b
    -- float32 a
    -- ================================================================================
    -- ASN.1 type for Visualization-msgs-Types/ImageMarker
    Visualization-msgs-ImageMarker ::= SEQUENCE
    {
        header Std-msgs-Header,
        ns T-String,
        id T-Int32,
        type-value T-Int32,
        action T-Int32,
        position Geometry-msgs-Point,
        scale T-Float,
        outline-color Std-msgs-ColorRGBA,
        filled T-UInt8,
        fill-color Std-msgs-ColorRGBA,
        lifetime T-Time,
        points SEQUENCE (SIZE(0..max-Visualization-msgs-ImageMarker)) OF Geometry-msgs-Point,
        outline-colors SEQUENCE (SIZE(0..max-Visualization-msgs-ImageMarker)) OF Std-msgs-ColorRGBA
    }
    -- ================================================================================

    -- ================================================================================
    -- Message Visualization-msgs-Types/InteractiveMarker
    -- ================================================================================
    -- # Time/frame info.
    -- # If header.time is set to 0, the marker will be retransformed into
    -- # its frame on each timestep. You will receive the pose feedback
    -- # in the same frame.
    -- # Otherwise, you might receive feedback in a different frame.
    -- # For rviz, this will be the current 'fixed frame' set by the user.
    -- Header header
    -- 
    -- # Initial pose. Also, defines the pivot point for rotations.
    -- geometry_msgs/Pose pose
    -- 
    -- # Identifying string. Must be globally unique in
    -- # the topic that this message is sent through.
    -- string name
    -- 
    -- # Short description (< 40 characters).
    -- string description
    -- 
    -- # Scale to be used for default controls (default=1).
    -- float32 scale
    -- 
    -- # All menu and submenu entries associated with this marker.
    -- MenuEntry[] menu_entries
    -- 
    -- # List of controls displayed for this marker.
    -- InteractiveMarkerControl[] controls
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: visualization_msgs/MenuEntry
    -- # MenuEntry message.
    -- 
    -- # Each InteractiveMarker message has an array of MenuEntry messages.
    -- # A collection of MenuEntries together describe a
    -- # menu/submenu/subsubmenu/etc tree, though they are stored in a flat
    -- # array.  The tree structure is represented by giving each menu entry
    -- # an ID number and a "parent_id" field.  Top-level entries are the
    -- # ones with parent_id = 0.  Menu entries are ordered within their
    -- # level the same way they are ordered in the containing array.  Parent
    -- # entries must appear before their children.
    -- 
    -- # Example:
    -- # - id = 3
    -- #   parent_id = 0
    -- #   title = "fun"
    -- # - id = 2
    -- #   parent_id = 0
    -- #   title = "robot"
    -- # - id = 4
    -- #   parent_id = 2
    -- #   title = "pr2"
    -- # - id = 5
    -- #   parent_id = 2
    -- #   title = "turtle"
    -- #
    -- # Gives a menu tree like this:
    -- #  - fun
    -- #  - robot
    -- #    - pr2
    -- #    - turtle
    -- 
    -- # ID is a number for each menu entry.  Must be unique within the
    -- # control, and should never be 0.
    -- uint32 id
    -- 
    -- # ID of the parent of this menu entry, if it is a submenu.  If this
    -- # menu entry is a top-level entry, set parent_id to 0.
    -- uint32 parent_id
    -- 
    -- # menu / entry title
    -- string title
    -- 
    -- # Arguments to command indicated by command_type (below)
    -- string command
    -- 
    -- # Command_type stores the type of response desired when this menu
    -- # entry is clicked.
    -- # FEEDBACK: send an InteractiveMarkerFeedback message with menu_entry_id set to this entry's id.
    -- # ROSRUN: execute "rosrun" with arguments given in the command field (above).
    -- # ROSLAUNCH: execute "roslaunch" with arguments given in the command field (above).
    -- uint8 FEEDBACK=0
    -- uint8 ROSRUN=1
    -- uint8 ROSLAUNCH=2
    -- uint8 command_type
    -- 
    -- ================================================================================
    -- MSG: visualization_msgs/InteractiveMarkerControl
    -- # Represents a control that is to be displayed together with an interactive marker
    -- 
    -- # Identifying string for this control.
    -- # You need to assign a unique value to this to receive feedback from the GUI
    -- # on what actions the user performs on this control (e.g. a button click).
    -- string name
    -- 
    -- 
    -- # Defines the local coordinate frame (relative to the pose of the parent
    -- # interactive marker) in which is being rotated and translated.
    -- # Default: Identity
    -- geometry_msgs/Quaternion orientation
    -- 
    -- 
    -- # Orientation mode: controls how orientation changes.
    -- # INHERIT: Follow orientation of interactive marker
    -- # FIXED: Keep orientation fixed at initial state
    -- # VIEW_FACING: Align y-z plane with screen (x: forward, y:left, z:up).
    -- uint8 INHERIT = 0 
    -- uint8 FIXED = 1
    -- uint8 VIEW_FACING = 2
    -- 
    -- uint8 orientation_mode
    -- 
    -- # Interaction mode for this control
    -- # 
    -- # NONE: This control is only meant for visualization; no context menu.
    -- # MENU: Like NONE, but right-click menu is active.
    -- # BUTTON: Element can be left-clicked.
    -- # MOVE_AXIS: Translate along local x-axis.
    -- # MOVE_PLANE: Translate in local y-z plane.
    -- # ROTATE_AXIS: Rotate around local x-axis.
    -- # MOVE_ROTATE: Combines MOVE_PLANE and ROTATE_AXIS.
    -- uint8 NONE = 0 
    -- uint8 MENU = 1
    -- uint8 BUTTON = 2
    -- uint8 MOVE_AXIS = 3 
    -- uint8 MOVE_PLANE = 4
    -- uint8 ROTATE_AXIS = 5
    -- uint8 MOVE_ROTATE = 6
    -- # "3D" interaction modes work with the mouse+SHIFT+CTRL or with 3D cursors.
    -- # MOVE_3D: Translate freely in 3D space.
    -- # ROTATE_3D: Rotate freely in 3D space about the origin of parent frame.
    -- # MOVE_ROTATE_3D: Full 6-DOF freedom of translation and rotation about the cursor origin.
    -- uint8 MOVE_3D = 7
    -- uint8 ROTATE_3D = 8
    -- uint8 MOVE_ROTATE_3D = 9
    -- 
    -- uint8 interaction_mode
    -- 
    -- 
    -- # If true, the contained markers will also be visible
    -- # when the gui is not in interactive mode.
    -- bool always_visible
    -- 
    -- 
    -- # Markers to be displayed as custom visual representation.
    -- # Leave this empty to use the default control handles.
    -- #
    -- # Note: 
    -- # - The markers can be defined in an arbitrary coordinate frame,
    -- #   but will be transformed into the local frame of the interactive marker.
    -- # - If the header of a marker is empty, its pose will be interpreted as 
    -- #   relative to the pose of the parent interactive marker.
    -- Marker[] markers
    -- 
    -- 
    -- # In VIEW_FACING mode, set this to true if you don't want the markers
    -- # to be aligned with the camera view point. The markers will show up
    -- # as in INHERIT mode.
    -- bool independent_marker_orientation
    -- 
    -- 
    -- # Short description (< 40 characters) of what this control does,
    -- # e.g. "Move the robot". 
    -- # Default: A generic description based on the interaction mode
    -- string description
    -- 
    -- ================================================================================
    -- MSG: visualization_msgs/Marker
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- ================================================================================
    -- ASN.1 type for Visualization-msgs-Types/InteractiveMarker
    Visualization-msgs-InteractiveMarker ::= SEQUENCE
    {
        header Std-msgs-Header,
        pose Geometry-msgs-Pose,
        name-value T-String,
        description T-String,
        scale T-Float,
        menu-entries SEQUENCE (SIZE(0..max-Visualization-msgs-InteractiveMarker)) OF Visualization-msgs-MenuEntry,
        controls SEQUENCE (SIZE(0..max-Visualization-msgs-InteractiveMarker)) OF Visualization-msgs-InteractiveMarkerControl
    }
    -- ================================================================================

    -- ================================================================================
    -- Message Visualization-msgs-Types/InteractiveMarkerControl
    -- ================================================================================
    -- # Represents a control that is to be displayed together with an interactive marker
    -- 
    -- # Identifying string for this control.
    -- # You need to assign a unique value to this to receive feedback from the GUI
    -- # on what actions the user performs on this control (e.g. a button click).
    -- string name
    -- 
    -- 
    -- # Defines the local coordinate frame (relative to the pose of the parent
    -- # interactive marker) in which is being rotated and translated.
    -- # Default: Identity
    -- geometry_msgs/Quaternion orientation
    -- 
    -- 
    -- # Orientation mode: controls how orientation changes.
    -- # INHERIT: Follow orientation of interactive marker
    -- # FIXED: Keep orientation fixed at initial state
    -- # VIEW_FACING: Align y-z plane with screen (x: forward, y:left, z:up).
    -- uint8 INHERIT = 0 
    -- uint8 FIXED = 1
    -- uint8 VIEW_FACING = 2
    -- 
    -- uint8 orientation_mode
    -- 
    -- # Interaction mode for this control
    -- # 
    -- # NONE: This control is only meant for visualization; no context menu.
    -- # MENU: Like NONE, but right-click menu is active.
    -- # BUTTON: Element can be left-clicked.
    -- # MOVE_AXIS: Translate along local x-axis.
    -- # MOVE_PLANE: Translate in local y-z plane.
    -- # ROTATE_AXIS: Rotate around local x-axis.
    -- # MOVE_ROTATE: Combines MOVE_PLANE and ROTATE_AXIS.
    -- uint8 NONE = 0 
    -- uint8 MENU = 1
    -- uint8 BUTTON = 2
    -- uint8 MOVE_AXIS = 3 
    -- uint8 MOVE_PLANE = 4
    -- uint8 ROTATE_AXIS = 5
    -- uint8 MOVE_ROTATE = 6
    -- # "3D" interaction modes work with the mouse+SHIFT+CTRL or with 3D cursors.
    -- # MOVE_3D: Translate freely in 3D space.
    -- # ROTATE_3D: Rotate freely in 3D space about the origin of parent frame.
    -- # MOVE_ROTATE_3D: Full 6-DOF freedom of translation and rotation about the cursor origin.
    -- uint8 MOVE_3D = 7
    -- uint8 ROTATE_3D = 8
    -- uint8 MOVE_ROTATE_3D = 9
    -- 
    -- uint8 interaction_mode
    -- 
    -- 
    -- # If true, the contained markers will also be visible
    -- # when the gui is not in interactive mode.
    -- bool always_visible
    -- 
    -- 
    -- # Markers to be displayed as custom visual representation.
    -- # Leave this empty to use the default control handles.
    -- #
    -- # Note: 
    -- # - The markers can be defined in an arbitrary coordinate frame,
    -- #   but will be transformed into the local frame of the interactive marker.
    -- # - If the header of a marker is empty, its pose will be interpreted as 
    -- #   relative to the pose of the parent interactive marker.
    -- Marker[] markers
    -- 
    -- 
    -- # In VIEW_FACING mode, set this to true if you don't want the markers
    -- # to be aligned with the camera view point. The markers will show up
    -- # as in INHERIT mode.
    -- bool independent_marker_orientation
    -- 
    -- 
    -- # Short description (< 40 characters) of what this control does,
    -- # e.g. "Move the robot". 
    -- # Default: A generic description based on the interaction mode
    -- string description
    -- 
    -- ================================================================================
    -- MSG: geometry_msgs/Quaternion
    -- # This represents an orientation in free space in quaternion form.
    -- 
    -- float64 x
    -- float64 y
    -- float64 z
    -- float64 w
    -- 
    -- ================================================================================
    -- MSG: visualization_msgs/Marker
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- ================================================================================
    -- ASN.1 type for Visualization-msgs-Types/InteractiveMarkerControl
    Visualization-msgs-InteractiveMarkerControl ::= SEQUENCE
    {
        name-value T-String,
        orientation Geometry-msgs-Quaternion,
        orientation-mode T-UInt8,
        interaction-mode T-UInt8,
        always-visible T-Boolean,
        markers SEQUENCE (SIZE(0..max-Visualization-msgs-InteractiveMarkerControl)) OF Visualization-msgs-Marker,
        independent-marker-orientation T-Boolean,
        description T-String
    }
    -- ================================================================================

    -- ================================================================================
    -- Message Visualization-msgs-Types/InteractiveMarkerFeedback
    -- ================================================================================
    -- # Time/frame info.
    -- Header header
    -- 
    -- # Identifying string. Must be unique in the topic namespace.
    -- string client_id
    -- 
    -- # Feedback message sent back from the GUI, e.g.
    -- # when the status of an interactive marker was modified by the user.
    -- 
    -- # Specifies which interactive marker and control this message refers to
    -- string marker_name
    -- string control_name
    -- 
    -- # Type of the event
    -- # KEEP_ALIVE: sent while dragging to keep up control of the marker
    -- # MENU_SELECT: a menu entry has been selected
    -- # BUTTON_CLICK: a button control has been clicked
    -- # POSE_UPDATE: the pose has been changed using one of the controls
    -- uint8 KEEP_ALIVE = 0
    -- uint8 POSE_UPDATE = 1
    -- uint8 MENU_SELECT = 2
    -- uint8 BUTTON_CLICK = 3
    -- 
    -- uint8 MOUSE_DOWN = 4
    -- uint8 MOUSE_UP = 5
    -- 
    -- uint8 event_type
    -- 
    -- # Current pose of the marker
    -- # Note: Has to be valid for all feedback types.
    -- geometry_msgs/Pose pose
    -- 
    -- # Contains the ID of the selected menu entry
    -- # Only valid for MENU_SELECT events.
    -- uint32 menu_entry_id
    -- 
    -- # If event_type is BUTTON_CLICK, MOUSE_DOWN, or MOUSE_UP, mouse_point
    -- # may contain the 3 dimensional position of the event on the
    -- # control.  If it does, mouse_point_valid will be true.  mouse_point
    -- # will be relative to the frame listed in the header.
    -- geometry_msgs/Point mouse_point
    -- bool mouse_point_valid
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Visualization-msgs-Types/InteractiveMarkerFeedback
    Visualization-msgs-InteractiveMarkerFeedback ::= SEQUENCE
    {
        header Std-msgs-Header,
        client-id T-String,
        marker-name T-String,
        control-name T-String,
        event-type T-UInt8,
        pose Geometry-msgs-Pose,
        menu-entry-id T-UInt32,
        mouse-point Geometry-msgs-Point,
        mouse-point-valid T-Boolean
    }
    -- ================================================================================

    -- ================================================================================
    -- Message Visualization-msgs-Types/InteractiveMarkerInit
    -- ================================================================================
    -- # Identifying string. Must be unique in the topic namespace
    -- # that this server works on.
    -- string server_id
    -- 
    -- # Sequence number.
    -- # The client will use this to detect if it has missed a subsequent
    -- # update.  Every update message will have the same sequence number as
    -- # an init message.  Clients will likely want to unsubscribe from the
    -- # init topic after a successful initialization to avoid receiving
    -- # duplicate data.
    -- uint64 seq_num
    -- 
    -- # All markers.
    -- InteractiveMarker[] markers
    -- 
    -- ================================================================================
    -- MSG: visualization_msgs/InteractiveMarker
    -- # Time/frame info.
    -- # If header.time is set to 0, the marker will be retransformed into
    -- # its frame on each timestep. You will receive the pose feedback
    -- # in the same frame.
    -- # Otherwise, you might receive feedback in a different frame.
    -- # For rviz, this will be the current 'fixed frame' set by the user.
    -- Header header
    -- 
    -- # Initial pose. Also, defines the pivot point for rotations.
    -- geometry_msgs/Pose pose
    -- 
    -- # Identifying string. Must be globally unique in
    -- # the topic that this message is sent through.
    -- string name
    -- 
    -- # Short description (< 40 characters).
    -- string description
    -- 
    -- # Scale to be used for default controls (default=1).
    -- float32 scale
    -- 
    -- # All menu and submenu entries associated with this marker.
    -- MenuEntry[] menu_entries
    -- 
    -- # List of controls displayed for this marker.
    -- InteractiveMarkerControl[] controls
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: visualization_msgs/MenuEntry
    -- # MenuEntry message.
    -- 
    -- # Each InteractiveMarker message has an array of MenuEntry messages.
    -- # A collection of MenuEntries together describe a
    -- # menu/submenu/subsubmenu/etc tree, though they are stored in a flat
    -- # array.  The tree structure is represented by giving each menu entry
    -- # an ID number and a "parent_id" field.  Top-level entries are the
    -- # ones with parent_id = 0.  Menu entries are ordered within their
    -- # level the same way they are ordered in the containing array.  Parent
    -- # entries must appear before their children.
    -- 
    -- # Example:
    -- # - id = 3
    -- #   parent_id = 0
    -- #   title = "fun"
    -- # - id = 2
    -- #   parent_id = 0
    -- #   title = "robot"
    -- # - id = 4
    -- #   parent_id = 2
    -- #   title = "pr2"
    -- # - id = 5
    -- #   parent_id = 2
    -- #   title = "turtle"
    -- #
    -- # Gives a menu tree like this:
    -- #  - fun
    -- #  - robot
    -- #    - pr2
    -- #    - turtle
    -- 
    -- # ID is a number for each menu entry.  Must be unique within the
    -- # control, and should never be 0.
    -- uint32 id
    -- 
    -- # ID of the parent of this menu entry, if it is a submenu.  If this
    -- # menu entry is a top-level entry, set parent_id to 0.
    -- uint32 parent_id
    -- 
    -- # menu / entry title
    -- string title
    -- 
    -- # Arguments to command indicated by command_type (below)
    -- string command
    -- 
    -- # Command_type stores the type of response desired when this menu
    -- # entry is clicked.
    -- # FEEDBACK: send an InteractiveMarkerFeedback message with menu_entry_id set to this entry's id.
    -- # ROSRUN: execute "rosrun" with arguments given in the command field (above).
    -- # ROSLAUNCH: execute "roslaunch" with arguments given in the command field (above).
    -- uint8 FEEDBACK=0
    -- uint8 ROSRUN=1
    -- uint8 ROSLAUNCH=2
    -- uint8 command_type
    -- 
    -- ================================================================================
    -- MSG: visualization_msgs/InteractiveMarkerControl
    -- # Represents a control that is to be displayed together with an interactive marker
    -- 
    -- # Identifying string for this control.
    -- # You need to assign a unique value to this to receive feedback from the GUI
    -- # on what actions the user performs on this control (e.g. a button click).
    -- string name
    -- 
    -- 
    -- # Defines the local coordinate frame (relative to the pose of the parent
    -- # interactive marker) in which is being rotated and translated.
    -- # Default: Identity
    -- geometry_msgs/Quaternion orientation
    -- 
    -- 
    -- # Orientation mode: controls how orientation changes.
    -- # INHERIT: Follow orientation of interactive marker
    -- # FIXED: Keep orientation fixed at initial state
    -- # VIEW_FACING: Align y-z plane with screen (x: forward, y:left, z:up).
    -- uint8 INHERIT = 0 
    -- uint8 FIXED = 1
    -- uint8 VIEW_FACING = 2
    -- 
    -- uint8 orientation_mode
    -- 
    -- # Interaction mode for this control
    -- # 
    -- # NONE: This control is only meant for visualization; no context menu.
    -- # MENU: Like NONE, but right-click menu is active.
    -- # BUTTON: Element can be left-clicked.
    -- # MOVE_AXIS: Translate along local x-axis.
    -- # MOVE_PLANE: Translate in local y-z plane.
    -- # ROTATE_AXIS: Rotate around local x-axis.
    -- # MOVE_ROTATE: Combines MOVE_PLANE and ROTATE_AXIS.
    -- uint8 NONE = 0 
    -- uint8 MENU = 1
    -- uint8 BUTTON = 2
    -- uint8 MOVE_AXIS = 3 
    -- uint8 MOVE_PLANE = 4
    -- uint8 ROTATE_AXIS = 5
    -- uint8 MOVE_ROTATE = 6
    -- # "3D" interaction modes work with the mouse+SHIFT+CTRL or with 3D cursors.
    -- # MOVE_3D: Translate freely in 3D space.
    -- # ROTATE_3D: Rotate freely in 3D space about the origin of parent frame.
    -- # MOVE_ROTATE_3D: Full 6-DOF freedom of translation and rotation about the cursor origin.
    -- uint8 MOVE_3D = 7
    -- uint8 ROTATE_3D = 8
    -- uint8 MOVE_ROTATE_3D = 9
    -- 
    -- uint8 interaction_mode
    -- 
    -- 
    -- # If true, the contained markers will also be visible
    -- # when the gui is not in interactive mode.
    -- bool always_visible
    -- 
    -- 
    -- # Markers to be displayed as custom visual representation.
    -- # Leave this empty to use the default control handles.
    -- #
    -- # Note: 
    -- # - The markers can be defined in an arbitrary coordinate frame,
    -- #   but will be transformed into the local frame of the interactive marker.
    -- # - If the header of a marker is empty, its pose will be interpreted as 
    -- #   relative to the pose of the parent interactive marker.
    -- Marker[] markers
    -- 
    -- 
    -- # In VIEW_FACING mode, set this to true if you don't want the markers
    -- # to be aligned with the camera view point. The markers will show up
    -- # as in INHERIT mode.
    -- bool independent_marker_orientation
    -- 
    -- 
    -- # Short description (< 40 characters) of what this control does,
    -- # e.g. "Move the robot". 
    -- # Default: A generic description based on the interaction mode
    -- string description
    -- 
    -- ================================================================================
    -- MSG: visualization_msgs/Marker
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- ================================================================================
    -- ASN.1 type for Visualization-msgs-Types/InteractiveMarkerInit
    Visualization-msgs-InteractiveMarkerInit ::= SEQUENCE
    {
        server-id T-String,
        seq-num T-UInt64,
        markers SEQUENCE (SIZE(0..max-Visualization-msgs-InteractiveMarkerInit)) OF Visualization-msgs-InteractiveMarker
    }
    -- ================================================================================

    -- ================================================================================
    -- Message Visualization-msgs-Types/InteractiveMarkerPose
    -- ================================================================================
    -- # Time/frame info.
    -- Header header
    -- 
    -- # Initial pose. Also, defines the pivot point for rotations.
    -- geometry_msgs/Pose pose
    -- 
    -- # Identifying string. Must be globally unique in
    -- # the topic that this message is sent through.
    -- string name
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Visualization-msgs-Types/InteractiveMarkerPose
    Visualization-msgs-InteractiveMarkerPose ::= SEQUENCE
    {
        header Std-msgs-Header,
        pose Geometry-msgs-Pose,
        name-value T-String
    }
    -- ================================================================================

    -- ================================================================================
    -- Message Visualization-msgs-Types/InteractiveMarkerUpdate
    -- ================================================================================
    -- # Identifying string. Must be unique in the topic namespace
    -- # that this server works on.
    -- string server_id
    -- 
    -- # Sequence number.
    -- # The client will use this to detect if it has missed an update.
    -- uint64 seq_num
    -- 
    -- # Type holds the purpose of this message.  It must be one of UPDATE or KEEP_ALIVE.
    -- # UPDATE: Incremental update to previous state. 
    -- #         The sequence number must be 1 higher than for
    -- #         the previous update.
    -- # KEEP_ALIVE: Indicates the that the server is still living.
    -- #             The sequence number does not increase.
    -- #             No payload data should be filled out (markers, poses, or erases).
    -- uint8 KEEP_ALIVE = 0
    -- uint8 UPDATE = 1
    -- 
    -- uint8 type
    -- 
    -- #Note: No guarantees on the order of processing.
    -- #      Contents must be kept consistent by sender.
    -- 
    -- #Markers to be added or updated
    -- InteractiveMarker[] markers
    -- 
    -- #Poses of markers that should be moved
    -- InteractiveMarkerPose[] poses
    -- 
    -- #Names of markers to be erased
    -- string[] erases
    -- 
    -- ================================================================================
    -- MSG: visualization_msgs/InteractiveMarker
    -- # Time/frame info.
    -- # If header.time is set to 0, the marker will be retransformed into
    -- # its frame on each timestep. You will receive the pose feedback
    -- # in the same frame.
    -- # Otherwise, you might receive feedback in a different frame.
    -- # For rviz, this will be the current 'fixed frame' set by the user.
    -- Header header
    -- 
    -- # Initial pose. Also, defines the pivot point for rotations.
    -- geometry_msgs/Pose pose
    -- 
    -- # Identifying string. Must be globally unique in
    -- # the topic that this message is sent through.
    -- string name
    -- 
    -- # Short description (< 40 characters).
    -- string description
    -- 
    -- # Scale to be used for default controls (default=1).
    -- float32 scale
    -- 
    -- # All menu and submenu entries associated with this marker.
    -- MenuEntry[] menu_entries
    -- 
    -- # List of controls displayed for this marker.
    -- InteractiveMarkerControl[] controls
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: visualization_msgs/MenuEntry
    -- # MenuEntry message.
    -- 
    -- # Each InteractiveMarker message has an array of MenuEntry messages.
    -- # A collection of MenuEntries together describe a
    -- # menu/submenu/subsubmenu/etc tree, though they are stored in a flat
    -- # array.  The tree structure is represented by giving each menu entry
    -- # an ID number and a "parent_id" field.  Top-level entries are the
    -- # ones with parent_id = 0.  Menu entries are ordered within their
    -- # level the same way they are ordered in the containing array.  Parent
    -- # entries must appear before their children.
    -- 
    -- # Example:
    -- # - id = 3
    -- #   parent_id = 0
    -- #   title = "fun"
    -- # - id = 2
    -- #   parent_id = 0
    -- #   title = "robot"
    -- # - id = 4
    -- #   parent_id = 2
    -- #   title = "pr2"
    -- # - id = 5
    -- #   parent_id = 2
    -- #   title = "turtle"
    -- #
    -- # Gives a menu tree like this:
    -- #  - fun
    -- #  - robot
    -- #    - pr2
    -- #    - turtle
    -- 
    -- # ID is a number for each menu entry.  Must be unique within the
    -- # control, and should never be 0.
    -- uint32 id
    -- 
    -- # ID of the parent of this menu entry, if it is a submenu.  If this
    -- # menu entry is a top-level entry, set parent_id to 0.
    -- uint32 parent_id
    -- 
    -- # menu / entry title
    -- string title
    -- 
    -- # Arguments to command indicated by command_type (below)
    -- string command
    -- 
    -- # Command_type stores the type of response desired when this menu
    -- # entry is clicked.
    -- # FEEDBACK: send an InteractiveMarkerFeedback message with menu_entry_id set to this entry's id.
    -- # ROSRUN: execute "rosrun" with arguments given in the command field (above).
    -- # ROSLAUNCH: execute "roslaunch" with arguments given in the command field (above).
    -- uint8 FEEDBACK=0
    -- uint8 ROSRUN=1
    -- uint8 ROSLAUNCH=2
    -- uint8 command_type
    -- 
    -- ================================================================================
    -- MSG: visualization_msgs/InteractiveMarkerControl
    -- # Represents a control that is to be displayed together with an interactive marker
    -- 
    -- # Identifying string for this control.
    -- # You need to assign a unique value to this to receive feedback from the GUI
    -- # on what actions the user performs on this control (e.g. a button click).
    -- string name
    -- 
    -- 
    -- # Defines the local coordinate frame (relative to the pose of the parent
    -- # interactive marker) in which is being rotated and translated.
    -- # Default: Identity
    -- geometry_msgs/Quaternion orientation
    -- 
    -- 
    -- # Orientation mode: controls how orientation changes.
    -- # INHERIT: Follow orientation of interactive marker
    -- # FIXED: Keep orientation fixed at initial state
    -- # VIEW_FACING: Align y-z plane with screen (x: forward, y:left, z:up).
    -- uint8 INHERIT = 0 
    -- uint8 FIXED = 1
    -- uint8 VIEW_FACING = 2
    -- 
    -- uint8 orientation_mode
    -- 
    -- # Interaction mode for this control
    -- # 
    -- # NONE: This control is only meant for visualization; no context menu.
    -- # MENU: Like NONE, but right-click menu is active.
    -- # BUTTON: Element can be left-clicked.
    -- # MOVE_AXIS: Translate along local x-axis.
    -- # MOVE_PLANE: Translate in local y-z plane.
    -- # ROTATE_AXIS: Rotate around local x-axis.
    -- # MOVE_ROTATE: Combines MOVE_PLANE and ROTATE_AXIS.
    -- uint8 NONE = 0 
    -- uint8 MENU = 1
    -- uint8 BUTTON = 2
    -- uint8 MOVE_AXIS = 3 
    -- uint8 MOVE_PLANE = 4
    -- uint8 ROTATE_AXIS = 5
    -- uint8 MOVE_ROTATE = 6
    -- # "3D" interaction modes work with the mouse+SHIFT+CTRL or with 3D cursors.
    -- # MOVE_3D: Translate freely in 3D space.
    -- # ROTATE_3D: Rotate freely in 3D space about the origin of parent frame.
    -- # MOVE_ROTATE_3D: Full 6-DOF freedom of translation and rotation about the cursor origin.
    -- uint8 MOVE_3D = 7
    -- uint8 ROTATE_3D = 8
    -- uint8 MOVE_ROTATE_3D = 9
    -- 
    -- uint8 interaction_mode
    -- 
    -- 
    -- # If true, the contained markers will also be visible
    -- # when the gui is not in interactive mode.
    -- bool always_visible
    -- 
    -- 
    -- # Markers to be displayed as custom visual representation.
    -- # Leave this empty to use the default control handles.
    -- #
    -- # Note: 
    -- # - The markers can be defined in an arbitrary coordinate frame,
    -- #   but will be transformed into the local frame of the interactive marker.
    -- # - If the header of a marker is empty, its pose will be interpreted as 
    -- #   relative to the pose of the parent interactive marker.
    -- Marker[] markers
    -- 
    -- 
    -- # In VIEW_FACING mode, set this to true if you don't want the markers
    -- # to be aligned with the camera view point. The markers will show up
    -- # as in INHERIT mode.
    -- bool independent_marker_orientation
    -- 
    -- 
    -- # Short description (< 40 characters) of what this control does,
    -- # e.g. "Move the robot". 
    -- # Default: A generic description based on the interaction mode
    -- string description
    -- 
    -- ================================================================================
    -- MSG: visualization_msgs/Marker
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- 
    -- ================================================================================
    -- MSG: visualization_msgs/InteractiveMarkerPose
    -- # Time/frame info.
    -- Header header
    -- 
    -- # Initial pose. Also, defines the pivot point for rotations.
    -- geometry_msgs/Pose pose
    -- 
    -- # Identifying string. Must be globally unique in
    -- # the topic that this message is sent through.
    -- string name
    -- ================================================================================
    -- ASN.1 type for Visualization-msgs-Types/InteractiveMarkerUpdate
    Visualization-msgs-InteractiveMarkerUpdate ::= SEQUENCE
    {
        server-id T-String,
        seq-num T-UInt64,
        type-value T-UInt8,
        markers SEQUENCE (SIZE(0..max-Visualization-msgs-InteractiveMarkerUpdate)) OF Visualization-msgs-InteractiveMarker,
        poses SEQUENCE (SIZE(0..max-Visualization-msgs-InteractiveMarkerUpdate)) OF Visualization-msgs-InteractiveMarkerPose,
        erases SEQUENCE (SIZE(0..max-Visualization-msgs-InteractiveMarkerUpdate)) OF T-String
    }
    -- ================================================================================

    -- ================================================================================
    -- Message Visualization-msgs-Types/Marker
    -- ================================================================================
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- ================================================================================
    -- ASN.1 type for Visualization-msgs-Types/Marker
    Visualization-msgs-Marker ::= SEQUENCE
    {
        header Std-msgs-Header,
        ns T-String,
        id T-Int32,
        type-value T-Int32,
        action T-Int32,
        pose Geometry-msgs-Pose,
        scale Geometry-msgs-Vector3,
        color Std-msgs-ColorRGBA,
        lifetime T-Time,
        frame-locked T-Boolean,
        points SEQUENCE (SIZE(0..max-Visualization-msgs-Marker)) OF Geometry-msgs-Point,
        colors SEQUENCE (SIZE(0..max-Visualization-msgs-Marker)) OF Std-msgs-ColorRGBA,
        text T-String,
        mesh-resource T-String,
        mesh-use-embedded-materials T-Boolean
    }
    -- ================================================================================

    -- ================================================================================
    -- Message Visualization-msgs-Types/MarkerArray
    -- ================================================================================
    -- Marker[] markers
    -- 
    -- ================================================================================
    -- MSG: visualization_msgs/Marker
    -- # See http://www.ros.org/wiki/rviz/DisplayTypes/Marker and http://www.ros.org/wiki/rviz/Tutorials/Markers%3A%20Basic%20Shapes for more information on using this message with rviz
    -- 
    -- uint8 ARROW=0
    -- uint8 CUBE=1
    -- uint8 SPHERE=2
    -- uint8 CYLINDER=3
    -- uint8 LINE_STRIP=4
    -- uint8 LINE_LIST=5
    -- uint8 CUBE_LIST=6
    -- uint8 SPHERE_LIST=7
    -- uint8 POINTS=8
    -- uint8 TEXT_VIEW_FACING=9
    -- uint8 MESH_RESOURCE=10
    -- uint8 TRIANGLE_LIST=11
    -- 
    -- uint8 ADD=0
    -- uint8 MODIFY=0
    -- uint8 DELETE=2
    -- uint8 DELETEALL=3
    -- 
    -- Header header                        # header for time/frame information
    -- string ns                            # Namespace to place this object in... used in conjunction with id to create a unique name for the object
    -- int32 id 		                         # object ID useful in conjunction with the namespace for manipulating and deleting the object later
    -- int32 type 		                       # Type of object
    -- int32 action 	                       # 0 add/modify an object, 1 (deprecated), 2 deletes an object, 3 deletes all objects
    -- geometry_msgs/Pose pose                 # Pose of the object
    -- geometry_msgs/Vector3 scale             # Scale of the object 1,1,1 means default (usually 1 meter square)
    -- std_msgs/ColorRGBA color             # Color [0.0-1.0]
    -- duration lifetime                    # How long the object should last before being automatically deleted.  0 means forever
    -- bool frame_locked                    # If this marker should be frame-locked, i.e. retransformed into its frame every timestep
    -- 
    -- #Only used if the type specified has some use for them (eg. POINTS, LINE_STRIP, ...)
    -- geometry_msgs/Point[] points
    -- #Only used if the type specified has some use for them (eg. POINTS, LINE_STRIP, ...)
    -- #number of colors must either be 0 or equal to the number of points
    -- #NOTE: alpha is not yet used
    -- std_msgs/ColorRGBA[] colors
    -- 
    -- # NOTE: only used for text markers
    -- string text
    -- 
    -- # NOTE: only used for MESH_RESOURCE markers
    -- string mesh_resource
    -- bool mesh_use_embedded_materials
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: std_msgs/ColorRGBA
    -- float32 r
    -- float32 g
    -- float32 b
    -- float32 a
    -- ================================================================================
    -- ASN.1 type for Visualization-msgs-Types/MarkerArray
    Visualization-msgs-MarkerArray ::= SEQUENCE (SIZE(0..max-Visualization-msgs-MarkerArray)) OF Visualization-msgs-Marker
    -- ================================================================================

    -- ================================================================================
    -- Message Visualization-msgs-Types/MenuEntry
    -- ================================================================================
    -- # MenuEntry message.
    -- 
    -- # Each InteractiveMarker message has an array of MenuEntry messages.
    -- # A collection of MenuEntries together describe a
    -- # menu/submenu/subsubmenu/etc tree, though they are stored in a flat
    -- # array.  The tree structure is represented by giving each menu entry
    -- # an ID number and a "parent_id" field.  Top-level entries are the
    -- # ones with parent_id = 0.  Menu entries are ordered within their
    -- # level the same way they are ordered in the containing array.  Parent
    -- # entries must appear before their children.
    -- 
    -- # Example:
    -- # - id = 3
    -- #   parent_id = 0
    -- #   title = "fun"
    -- # - id = 2
    -- #   parent_id = 0
    -- #   title = "robot"
    -- # - id = 4
    -- #   parent_id = 2
    -- #   title = "pr2"
    -- # - id = 5
    -- #   parent_id = 2
    -- #   title = "turtle"
    -- #
    -- # Gives a menu tree like this:
    -- #  - fun
    -- #  - robot
    -- #    - pr2
    -- #    - turtle
    -- 
    -- # ID is a number for each menu entry.  Must be unique within the
    -- # control, and should never be 0.
    -- uint32 id
    -- 
    -- # ID of the parent of this menu entry, if it is a submenu.  If this
    -- # menu entry is a top-level entry, set parent_id to 0.
    -- uint32 parent_id
    -- 
    -- # menu / entry title
    -- string title
    -- 
    -- # Arguments to command indicated by command_type (below)
    -- string command
    -- 
    -- # Command_type stores the type of response desired when this menu
    -- # entry is clicked.
    -- # FEEDBACK: send an InteractiveMarkerFeedback message with menu_entry_id set to this entry's id.
    -- # ROSRUN: execute "rosrun" with arguments given in the command field (above).
    -- # ROSLAUNCH: execute "roslaunch" with arguments given in the command field (above).
    -- uint8 FEEDBACK=0
    -- uint8 ROSRUN=1
    -- uint8 ROSLAUNCH=2
    -- uint8 command_type
    -- ================================================================================
    -- ASN.1 type for Visualization-msgs-Types/MenuEntry
    Visualization-msgs-MenuEntry ::= SEQUENCE
    {
        id T-UInt32,
        parent-id T-UInt32,
        title T-String,
        command T-String,
        command-type T-UInt8
    }
    -- ================================================================================

END
