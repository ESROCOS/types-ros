-- Generated from package.asn.mako for package std_msgs

Std-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
max-Std-msgs-UInt8MultiArray, max-Std-msgs-Int16MultiArray, max-Std-msgs-Int32MultiArray, max-Std-msgs-Float32MultiArray, max-Std-msgs-UInt16MultiArray, max-Std-msgs-ByteMultiArray, max-Std-msgs-MultiArrayLayout, max-Std-msgs-Float64MultiArray, max-Std-msgs-Int8MultiArray, max-Std-msgs-UInt64MultiArray, max-Std-msgs-Int64MultiArray, max-Std-msgs-UInt32MultiArray, Dummy-Std-msgs-Types-T FROM UserDefs-Std-msgs-Types;
    -- ================================================================================
    -- Message Std-msgs-Types/Bool
    -- ================================================================================
    -- bool data    -- ================================================================================
    -- ASN.1 type for Std-msgs-Types/Bool
    Std-msgs-Bool ::= T-Boolean

    -- ================================================================================

    -- ================================================================================
    -- Message Std-msgs-Types/Byte
    -- ================================================================================
    -- byte data
    -- ================================================================================
    -- ASN.1 type for Std-msgs-Types/Byte
    Std-msgs-Byte ::= T-Int8

    -- ================================================================================

    -- ================================================================================
    -- Message Std-msgs-Types/ByteMultiArray
    -- ================================================================================
    -- # Please look at the MultiArrayLayout message definition for
    -- # documentation on all multiarrays.
    -- 
    -- MultiArrayLayout  layout        # specification of data layout
    -- byte[]            data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/ByteMultiArray
    Std-msgs-ByteMultiArray ::= SEQUENCE
    {
        layout Std-msgs-MultiArrayLayout,
        data-value OCTET STRING (SIZE(0..max-Std-msgs-ByteMultiArray))
    }
    -- ================================================================================

    -- ================================================================================
    -- Message Std-msgs-Types/Char
    -- ================================================================================
    -- char data    -- ================================================================================
    -- ASN.1 type for Std-msgs-Types/Char
    Std-msgs-Char ::= T-UInt8

    -- ================================================================================

    -- ================================================================================
    -- Message Std-msgs-Types/ColorRGBA
    -- ================================================================================
    -- float32 r
    -- float32 g
    -- float32 b
    -- float32 a
    -- ================================================================================
    -- ASN.1 type for Std-msgs-Types/ColorRGBA
    Std-msgs-ColorRGBA ::= SEQUENCE
    {
        r T-Float,
        g T-Float,
        b T-Float,
        a T-Float
    }
    -- ================================================================================

    -- ================================================================================
    -- Message Std-msgs-Types/Duration
    -- ================================================================================
    -- duration data
    -- ================================================================================
    -- ASN.1 type for Std-msgs-Types/Duration
    Std-msgs-Duration ::= T-Time

    -- ================================================================================

    -- ================================================================================
    -- Message Std-msgs-Types/Empty
    -- ================================================================================
    -- ================================================================================
    -- ASN.1 type for Std-msgs-Types/Empty
    Std-msgs-Empty ::= SEQUENCE
    {
    }
    -- ================================================================================

    -- ================================================================================
    -- Message Std-msgs-Types/Float32
    -- ================================================================================
    -- float32 data    -- ================================================================================
    -- ASN.1 type for Std-msgs-Types/Float32
    Std-msgs-Float32 ::= T-Float

    -- ================================================================================

    -- ================================================================================
    -- Message Std-msgs-Types/Float32MultiArray
    -- ================================================================================
    -- # Please look at the MultiArrayLayout message definition for
    -- # documentation on all multiarrays.
    -- 
    -- MultiArrayLayout  layout        # specification of data layout
    -- float32[]         data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Float32MultiArray
    Std-msgs-Float32MultiArray ::= SEQUENCE
    {
        layout Std-msgs-MultiArrayLayout,
        data-value SEQUENCE (SIZE(0..max-Std-msgs-Float32MultiArray)) OF T-Float
    }
    -- ================================================================================

    -- ================================================================================
    -- Message Std-msgs-Types/Float64
    -- ================================================================================
    -- float64 data    -- ================================================================================
    -- ASN.1 type for Std-msgs-Types/Float64
    Std-msgs-Float64 ::= T-Double

    -- ================================================================================

    -- ================================================================================
    -- Message Std-msgs-Types/Float64MultiArray
    -- ================================================================================
    -- # Please look at the MultiArrayLayout message definition for
    -- # documentation on all multiarrays.
    -- 
    -- MultiArrayLayout  layout        # specification of data layout
    -- float64[]         data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Float64MultiArray
    Std-msgs-Float64MultiArray ::= SEQUENCE
    {
        layout Std-msgs-MultiArrayLayout,
        data-value SEQUENCE (SIZE(0..max-Std-msgs-Float64MultiArray)) OF T-Double
    }
    -- ================================================================================

    -- ================================================================================
    -- Message Std-msgs-Types/Header
    -- ================================================================================
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Std-msgs-Types/Header
    Std-msgs-Header ::= SEQUENCE
    {
        seq T-UInt32,
        stamp T-Time,
        frame-id T-String
    }
    -- ================================================================================

    -- ================================================================================
    -- Message Std-msgs-Types/Int16
    -- ================================================================================
    -- int16 data
    -- ================================================================================
    -- ASN.1 type for Std-msgs-Types/Int16
    Std-msgs-Int16 ::= T-Int16

    -- ================================================================================

    -- ================================================================================
    -- Message Std-msgs-Types/Int16MultiArray
    -- ================================================================================
    -- # Please look at the MultiArrayLayout message definition for
    -- # documentation on all multiarrays.
    -- 
    -- MultiArrayLayout  layout        # specification of data layout
    -- int16[]           data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Int16MultiArray
    Std-msgs-Int16MultiArray ::= SEQUENCE
    {
        layout Std-msgs-MultiArrayLayout,
        data-value SEQUENCE (SIZE(0..max-Std-msgs-Int16MultiArray)) OF T-Int16
    }
    -- ================================================================================

    -- ================================================================================
    -- Message Std-msgs-Types/Int32
    -- ================================================================================
    -- int32 data    -- ================================================================================
    -- ASN.1 type for Std-msgs-Types/Int32
    Std-msgs-Int32 ::= T-Int32

    -- ================================================================================

    -- ================================================================================
    -- Message Std-msgs-Types/Int32MultiArray
    -- ================================================================================
    -- # Please look at the MultiArrayLayout message definition for
    -- # documentation on all multiarrays.
    -- 
    -- MultiArrayLayout  layout        # specification of data layout
    -- int32[]           data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Int32MultiArray
    Std-msgs-Int32MultiArray ::= SEQUENCE
    {
        layout Std-msgs-MultiArrayLayout,
        data-value SEQUENCE (SIZE(0..max-Std-msgs-Int32MultiArray)) OF T-Int32
    }
    -- ================================================================================

    -- ================================================================================
    -- Message Std-msgs-Types/Int64
    -- ================================================================================
    -- int64 data    -- ================================================================================
    -- ASN.1 type for Std-msgs-Types/Int64
    Std-msgs-Int64 ::= T-Int64

    -- ================================================================================

    -- ================================================================================
    -- Message Std-msgs-Types/Int64MultiArray
    -- ================================================================================
    -- # Please look at the MultiArrayLayout message definition for
    -- # documentation on all multiarrays.
    -- 
    -- MultiArrayLayout  layout        # specification of data layout
    -- int64[]           data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Int64MultiArray
    Std-msgs-Int64MultiArray ::= SEQUENCE
    {
        layout Std-msgs-MultiArrayLayout,
        data-value SEQUENCE (SIZE(0..max-Std-msgs-Int64MultiArray)) OF T-Int64
    }
    -- ================================================================================

    -- ================================================================================
    -- Message Std-msgs-Types/Int8
    -- ================================================================================
    -- int8 data
    -- ================================================================================
    -- ASN.1 type for Std-msgs-Types/Int8
    Std-msgs-Int8 ::= T-Int8

    -- ================================================================================

    -- ================================================================================
    -- Message Std-msgs-Types/Int8MultiArray
    -- ================================================================================
    -- # Please look at the MultiArrayLayout message definition for
    -- # documentation on all multiarrays.
    -- 
    -- MultiArrayLayout  layout        # specification of data layout
    -- int8[]            data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/Int8MultiArray
    Std-msgs-Int8MultiArray ::= SEQUENCE
    {
        layout Std-msgs-MultiArrayLayout,
        data-value SEQUENCE (SIZE(0..max-Std-msgs-Int8MultiArray)) OF T-Int8
    }
    -- ================================================================================

    -- ================================================================================
    -- Message Std-msgs-Types/MultiArrayDimension
    -- ================================================================================
    -- string label   # label of given dimension
    -- uint32 size    # size of given dimension (in type units)
    -- uint32 stride  # stride of given dimension    -- ================================================================================
    -- ASN.1 type for Std-msgs-Types/MultiArrayDimension
    Std-msgs-MultiArrayDimension ::= SEQUENCE
    {
        label T-String,
        size-value T-UInt32,
        stride T-UInt32
    }
    -- ================================================================================

    -- ================================================================================
    -- Message Std-msgs-Types/MultiArrayLayout
    -- ================================================================================
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/MultiArrayLayout
    Std-msgs-MultiArrayLayout ::= SEQUENCE
    {
        dim SEQUENCE (SIZE(0..max-Std-msgs-MultiArrayLayout)) OF Std-msgs-MultiArrayDimension,
        data-offset T-UInt32
    }
    -- ================================================================================

    -- ================================================================================
    -- Message Std-msgs-Types/String
    -- ================================================================================
    -- string data
    -- ================================================================================
    -- ASN.1 type for Std-msgs-Types/String
    Std-msgs-String ::= T-String

    -- ================================================================================

    -- ================================================================================
    -- Message Std-msgs-Types/Time
    -- ================================================================================
    -- time data
    -- ================================================================================
    -- ASN.1 type for Std-msgs-Types/Time
    Std-msgs-Time ::= T-Time

    -- ================================================================================

    -- ================================================================================
    -- Message Std-msgs-Types/UInt16
    -- ================================================================================
    -- uint16 data
    -- ================================================================================
    -- ASN.1 type for Std-msgs-Types/UInt16
    Std-msgs-UInt16 ::= T-UInt16

    -- ================================================================================

    -- ================================================================================
    -- Message Std-msgs-Types/UInt16MultiArray
    -- ================================================================================
    -- # Please look at the MultiArrayLayout message definition for
    -- # documentation on all multiarrays.
    -- 
    -- MultiArrayLayout  layout        # specification of data layout
    -- uint16[]            data        # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/UInt16MultiArray
    Std-msgs-UInt16MultiArray ::= SEQUENCE
    {
        layout Std-msgs-MultiArrayLayout,
        data-value SEQUENCE (SIZE(0..max-Std-msgs-UInt16MultiArray)) OF T-UInt16
    }
    -- ================================================================================

    -- ================================================================================
    -- Message Std-msgs-Types/UInt32
    -- ================================================================================
    -- uint32 data    -- ================================================================================
    -- ASN.1 type for Std-msgs-Types/UInt32
    Std-msgs-UInt32 ::= T-UInt32

    -- ================================================================================

    -- ================================================================================
    -- Message Std-msgs-Types/UInt32MultiArray
    -- ================================================================================
    -- # Please look at the MultiArrayLayout message definition for
    -- # documentation on all multiarrays.
    -- 
    -- MultiArrayLayout  layout        # specification of data layout
    -- uint32[]          data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/UInt32MultiArray
    Std-msgs-UInt32MultiArray ::= SEQUENCE
    {
        layout Std-msgs-MultiArrayLayout,
        data-value SEQUENCE (SIZE(0..max-Std-msgs-UInt32MultiArray)) OF T-UInt32
    }
    -- ================================================================================

    -- ================================================================================
    -- Message Std-msgs-Types/UInt64
    -- ================================================================================
    -- uint64 data    -- ================================================================================
    -- ASN.1 type for Std-msgs-Types/UInt64
    Std-msgs-UInt64 ::= T-UInt64

    -- ================================================================================

    -- ================================================================================
    -- Message Std-msgs-Types/UInt64MultiArray
    -- ================================================================================
    -- # Please look at the MultiArrayLayout message definition for
    -- # documentation on all multiarrays.
    -- 
    -- MultiArrayLayout  layout        # specification of data layout
    -- uint64[]          data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/UInt64MultiArray
    Std-msgs-UInt64MultiArray ::= SEQUENCE
    {
        layout Std-msgs-MultiArrayLayout,
        data-value SEQUENCE (SIZE(0..max-Std-msgs-UInt64MultiArray)) OF T-UInt64
    }
    -- ================================================================================

    -- ================================================================================
    -- Message Std-msgs-Types/UInt8
    -- ================================================================================
    -- uint8 data
    -- ================================================================================
    -- ASN.1 type for Std-msgs-Types/UInt8
    Std-msgs-UInt8 ::= T-UInt8

    -- ================================================================================

    -- ================================================================================
    -- Message Std-msgs-Types/UInt8MultiArray
    -- ================================================================================
    -- # Please look at the MultiArrayLayout message definition for
    -- # documentation on all multiarrays.
    -- 
    -- MultiArrayLayout  layout        # specification of data layout
    -- uint8[]           data          # array of data
    -- 
    -- 
    -- ================================================================================
    -- MSG: std_msgs/MultiArrayLayout
    -- # The multiarray declares a generic multi-dimensional array of a
    -- # particular data type.  Dimensions are ordered from outer most
    -- # to inner most.
    -- 
    -- MultiArrayDimension[] dim # Array of dimension properties
    -- uint32 data_offset        # padding elements at front of data
    -- 
    -- # Accessors should ALWAYS be written in terms of dimension stride
    -- # and specified outer-most dimension first.
    -- # 
    -- # multiarray(i,j,k) = data[data_offset + dim_stride[1]*i + dim_stride[2]*j + k]
    -- #
    -- # A standard, 3-channel 640x480 image with interleaved color channels
    -- # would be specified as:
    -- #
    -- # dim[0].label  = "height"
    -- # dim[0].size   = 480
    -- # dim[0].stride = 3*640*480 = 921600  (note dim[0] stride is just size of image)
    -- # dim[1].label  = "width"
    -- # dim[1].size   = 640
    -- # dim[1].stride = 3*640 = 1920
    -- # dim[2].label  = "channel"
    -- # dim[2].size   = 3
    -- # dim[2].stride = 3
    -- #
    -- # multiarray(i,j,k) refers to the ith row, jth column, and kth channel.
    -- 
    -- ================================================================================
    -- MSG: std_msgs/MultiArrayDimension
    -- string label   # label of given dimension
    -- uint32 size    # size of given dimension (in type units)
    -- uint32 stride  # stride of given dimension    -- ================================================================================
    -- ASN.1 type for Std-msgs-Types/UInt8MultiArray
    Std-msgs-UInt8MultiArray ::= SEQUENCE
    {
        layout Std-msgs-MultiArrayLayout,
        data-value OCTET STRING (SIZE(0..max-Std-msgs-UInt8MultiArray))
    }
    -- ================================================================================

END
