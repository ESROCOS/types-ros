-- Generated from package.asn.mako for package trajectory_msgs

Trajectory-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Geometry-msgs-Twist, Geometry-msgs-Transform FROM Geometry-msgs-Types
Std-msgs-Header FROM Std-msgs-Types
max-Trajectory-msgs-JointTrajectory, max-Trajectory-msgs-MultiDOFJointTrajectoryPoint, max-Trajectory-msgs-MultiDOFJointTrajectory, max-Trajectory-msgs-JointTrajectoryPoint, Dummy-Trajectory-msgs-Types-T FROM UserDefs-Trajectory-msgs-Types;
    -- ================================================================================
    -- Message Trajectory-msgs-Types/JointTrajectory
    -- ================================================================================
    -- Header header
    -- string[] joint_names
    -- JointTrajectoryPoint[] points
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/JointTrajectoryPoint
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Trajectory-msgs-Types/JointTrajectory
    Trajectory-msgs-JointTrajectory ::= SEQUENCE
    {
        header Std-msgs-Header,
        joint-names SEQUENCE (SIZE(0..max-Trajectory-msgs-JointTrajectory)) OF T-String,
        points SEQUENCE (SIZE(0..max-Trajectory-msgs-JointTrajectory)) OF Trajectory-msgs-JointTrajectoryPoint
    }
    -- ================================================================================

    -- ================================================================================
    -- Message Trajectory-msgs-Types/JointTrajectoryPoint
    -- ================================================================================
    -- # Each trajectory point specifies either positions[, velocities[, accelerations]]
    -- # or positions[, effort] for the trajectory to be executed.
    -- # All specified values are in the same order as the joint names in JointTrajectory.msg
    -- 
    -- float64[] positions
    -- float64[] velocities
    -- float64[] accelerations
    -- float64[] effort
    -- duration time_from_start
    -- ================================================================================
    -- ASN.1 type for Trajectory-msgs-Types/JointTrajectoryPoint
    Trajectory-msgs-JointTrajectoryPoint ::= SEQUENCE
    {
        positions SEQUENCE (SIZE(0..max-Trajectory-msgs-JointTrajectoryPoint)) OF T-Double,
        velocities SEQUENCE (SIZE(0..max-Trajectory-msgs-JointTrajectoryPoint)) OF T-Double,
        accelerations SEQUENCE (SIZE(0..max-Trajectory-msgs-JointTrajectoryPoint)) OF T-Double,
        effort SEQUENCE (SIZE(0..max-Trajectory-msgs-JointTrajectoryPoint)) OF T-Double,
        time-from-start T-Time
    }
    -- ================================================================================

    -- ================================================================================
    -- Message Trajectory-msgs-Types/MultiDOFJointTrajectory
    -- ================================================================================
    -- # The header is used to specify the coordinate frame and the reference time for the trajectory durations
    -- Header header
    -- 
    -- # A representation of a multi-dof joint trajectory (each point is a transformation)
    -- # Each point along the trajectory will include an array of positions/velocities/accelerations
    -- # that has the same length as the array of joint names, and has the same order of joints as 
    -- # the joint names array.
    -- 
    -- string[] joint_names
    -- MultiDOFJointTrajectoryPoint[] points
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: trajectory_msgs/MultiDOFJointTrajectoryPoint
    -- # Each multi-dof joint can specify a transform (up to 6 DOF)
    -- geometry_msgs/Transform[] transforms
    -- 
    -- # There can be a velocity specified for the origin of the joint 
    -- geometry_msgs/Twist[] velocities
    -- 
    -- # There can be an acceleration specified for the origin of the joint 
    -- geometry_msgs/Twist[] accelerations
    -- 
    -- duration time_from_start
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- 
    -- ================================================================================
    -- MSG: geometry_msgs/Twist
    -- # This expresses velocity in free space broken into its linear and angular parts.
    -- Vector3  linear
    -- Vector3  angular
    -- ================================================================================
    -- ASN.1 type for Trajectory-msgs-Types/MultiDOFJointTrajectory
    Trajectory-msgs-MultiDOFJointTrajectory ::= SEQUENCE
    {
        header Std-msgs-Header,
        joint-names SEQUENCE (SIZE(0..max-Trajectory-msgs-MultiDOFJointTrajectory)) OF T-String,
        points SEQUENCE (SIZE(0..max-Trajectory-msgs-MultiDOFJointTrajectory)) OF Trajectory-msgs-MultiDOFJointTrajectoryPoint
    }
    -- ================================================================================

    -- ================================================================================
    -- Message Trajectory-msgs-Types/MultiDOFJointTrajectoryPoint
    -- ================================================================================
    -- # Each multi-dof joint can specify a transform (up to 6 DOF)
    -- geometry_msgs/Transform[] transforms
    -- 
    -- # There can be a velocity specified for the origin of the joint 
    -- geometry_msgs/Twist[] velocities
    -- 
    -- # There can be an acceleration specified for the origin of the joint 
    -- geometry_msgs/Twist[] accelerations
    -- 
    -- duration time_from_start
    -- 
    -- ================================================================================
    -- MSG: geometry_msgs/Transform
    -- # This represents the transform between two coordinate frames in free space.
    -- 
    -- Vector3 translation
    -- Quaternion rotation
    -- 
    -- ================================================================================
    -- MSG: geometry_msgs/Vector3
    -- # This represents a vector in free space. 
    -- # It is only meant to represent a direction. Therefore, it does not
    -- # make sense to apply a translation to it (e.g., when applying a 
    -- # generic rigid transformation to a Vector3, tf2 will only apply the
    -- # rotation). If you want your data to be translatable too, use the
    -- # geometry_msgs/Point message instead.
    -- 
    -- float64 x
    -- float64 y
    -- float64 z
    -- ================================================================================
    -- MSG: geometry_msgs/Quaternion
    -- # This represents an orientation in free space in quaternion form.
    -- 
    -- float64 x
    -- float64 y
    -- float64 z
    -- float64 w
    -- 
    -- ================================================================================
    -- MSG: geometry_msgs/Twist
    -- # This expresses velocity in free space broken into its linear and angular parts.
    -- Vector3  linear
    -- Vector3  angular
    -- ================================================================================
    -- ASN.1 type for Trajectory-msgs-Types/MultiDOFJointTrajectoryPoint
    Trajectory-msgs-MultiDOFJointTrajectoryPoint ::= SEQUENCE
    {
        transforms SEQUENCE (SIZE(0..max-Trajectory-msgs-MultiDOFJointTrajectoryPoint)) OF Geometry-msgs-Transform,
        velocities SEQUENCE (SIZE(0..max-Trajectory-msgs-MultiDOFJointTrajectoryPoint)) OF Geometry-msgs-Twist,
        accelerations SEQUENCE (SIZE(0..max-Trajectory-msgs-MultiDOFJointTrajectoryPoint)) OF Geometry-msgs-Twist,
        time-from-start T-Time
    }
    -- ================================================================================

END
