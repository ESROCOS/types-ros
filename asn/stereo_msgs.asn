-- Generated from package.asn.mako for package stereo_msgs

Stereo-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Sensor-msgs-RegionOfInterest, Sensor-msgs-Image FROM Sensor-msgs-Types
Std-msgs-Header FROM Std-msgs-Types
;
    -- ================================================================================
    -- Message Stereo-msgs-Types/DisparityImage
    -- ================================================================================
    -- # Separate header for compatibility with current TimeSynchronizer.
    -- # Likely to be removed in a later release, use image.header instead.
    -- Header header
    -- 
    -- # Floating point disparity image. The disparities are pre-adjusted for any
    -- # x-offset between the principal points of the two cameras (in the case
    -- # that they are verged). That is: d = x_l - x_r - (cx_l - cx_r)
    -- sensor_msgs/Image image
    -- 
    -- # Stereo geometry. For disparity d, the depth from the camera is Z = fT/d.
    -- float32 f # Focal length, pixels
    -- float32 T # Baseline, world units
    -- 
    -- # Subwindow of (potentially) valid disparity values.
    -- sensor_msgs/RegionOfInterest valid_window
    -- 
    -- # The range of disparities searched.
    -- # In the disparity image, any disparity less than min_disparity is invalid.
    -- # The disparity search range defines the horopter, or 3D volume that the
    -- # stereo algorithm can "see". Points with Z outside of:
    -- #     Z_min = fT / max_disparity
    -- #     Z_max = fT / min_disparity
    -- # could not be found.
    -- float32 min_disparity
    -- float32 max_disparity
    -- 
    -- # Smallest allowed disparity increment. The smallest achievable depth range
    -- # resolution is delta_Z = (Z^2/fT)*delta_d.
    -- float32 delta_d
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: sensor_msgs/Image
    -- # This message contains an uncompressed image
    -- # (0, 0) is at top-left corner of image
    -- #
    -- 
    -- Header header        # Header timestamp should be acquisition time of image
    --                      # Header frame_id should be optical frame of camera
    --                      # origin of frame should be optical center of cameara
    --                      # +x should point to the right in the image
    --                      # +y should point down in the image
    --                      # +z should point into to plane of the image
    --                      # If the frame_id here and the frame_id of the CameraInfo
    --                      # message associated with the image conflict
    --                      # the behavior is undefined
    -- 
    -- uint32 height         # image height, that is, number of rows
    -- uint32 width          # image width, that is, number of columns
    -- 
    -- # The legal values for encoding are in file src/image_encodings.cpp
    -- # If you want to standardize a new string format, join
    -- # ros-users@lists.sourceforge.net and send an email proposing a new encoding.
    -- 
    -- string encoding       # Encoding of pixels -- channel meaning, ordering, size
    --                       # taken from the list of strings in include/sensor_msgs/image_encodings.h
    -- 
    -- uint8 is_bigendian    # is this data bigendian?
    -- uint32 step           # Full row length in bytes
    -- uint8[] data          # actual matrix data, size is (step * rows)
    -- 
    -- ================================================================================
    -- MSG: sensor_msgs/RegionOfInterest
    -- # This message is used to specify a region of interest within an image.
    -- #
    -- # When used to specify the ROI setting of the camera when the image was
    -- # taken, the height and width fields should either match the height and
    -- # width fields for the associated image; or height = width = 0
    -- # indicates that the full resolution image was captured.
    -- 
    -- uint32 x_offset  # Leftmost pixel of the ROI
    --                  # (0 if the ROI includes the left edge of the image)
    -- uint32 y_offset  # Topmost pixel of the ROI
    --                  # (0 if the ROI includes the top edge of the image)
    -- uint32 height    # Height of ROI
    -- uint32 width     # Width of ROI
    -- 
    -- # True if a distinct rectified ROI should be calculated from the "raw"
    -- # ROI in this message. Typically this should be False if the full image
    -- # is captured (ROI not used), and True if a subwindow is captured (ROI
    -- # used).
    -- bool do_rectify
    -- ================================================================================
    -- ASN.1 type for Stereo-msgs-Types/DisparityImage
    Stereo-msgs-DisparityImage ::= SEQUENCE
    {
        header Std-msgs-Header,
        image Sensor-msgs-Image,
        f T-Float,
        t T-Float,
        valid-window Sensor-msgs-RegionOfInterest,
        min-disparity T-Float,
        max-disparity T-Float,
        delta-d T-Float
    }
    -- ================================================================================

END
