-- Generated from package.asn.mako for package smach_msgs

Smach-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Std-msgs-Header FROM Std-msgs-Types
max-Smach-msgs-SmachContainerStatus, max-Smach-msgs-SmachContainerInitialStatusCmd, max-Smach-msgs-SmachContainerStructure, Dummy-Smach-msgs-Types-T FROM UserDefs-Smach-msgs-Types;
    -- ================================================================================
    -- Message Smach-msgs-Types/SmachContainerInitialStatusCmd
    -- ================================================================================
    -- # The path to the node in the server
    -- string path
    -- 
    -- # The desired initial state(s)
    -- string[] initial_states
    -- 
    -- # Initial values for the local user data of the state machine
    -- # A pickled user data structure
    -- # i.e. the UserData's internal dictionary
    -- string local_data
    -- ================================================================================
    -- ASN.1 type for Smach-msgs-Types/SmachContainerInitialStatusCmd
    Smach-msgs-SmachContainerInitialStatusCmd ::= SEQUENCE
    {
        path T-String,
        initial-states SEQUENCE (SIZE(0..max-Smach-msgs-SmachContainerInitialStatusCmd)) OF T-String,
        local-data T-String
    }
    -- ================================================================================

    -- ================================================================================
    -- Message Smach-msgs-Types/SmachContainerStatus
    -- ================================================================================
    -- Header header
    -- 
    -- # The path to this node in the server
    -- string path
    -- 
    -- # The initial state description
    -- # Effects an arc from the top state to each one
    -- string[] initial_states
    -- 
    -- # The current state description
    -- string[] active_states
    -- 
    -- # A pickled user data structure
    -- # i.e. the UserData's internal dictionary
    -- string local_data
    -- 
    -- # Debugging info string
    -- string info
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Smach-msgs-Types/SmachContainerStatus
    Smach-msgs-SmachContainerStatus ::= SEQUENCE
    {
        header Std-msgs-Header,
        path T-String,
        initial-states SEQUENCE (SIZE(0..max-Smach-msgs-SmachContainerStatus)) OF T-String,
        active-states SEQUENCE (SIZE(0..max-Smach-msgs-SmachContainerStatus)) OF T-String,
        local-data T-String,
        info T-String
    }
    -- ================================================================================

    -- ================================================================================
    -- Message Smach-msgs-Types/SmachContainerStructure
    -- ================================================================================
    -- Header header
    -- 
    -- # The path to this node in the server
    -- string path
    -- 
    -- # The children of this node
    -- string[] children
    -- 
    -- # The outcome edges
    -- # Each index across these arrays denote one edge
    -- string[] internal_outcomes
    -- string[] outcomes_from
    -- string[] outcomes_to
    -- 
    -- # The potential outcomes from this container
    -- string[] container_outcomes
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Smach-msgs-Types/SmachContainerStructure
    Smach-msgs-SmachContainerStructure ::= SEQUENCE
    {
        header Std-msgs-Header,
        path T-String,
        children SEQUENCE (SIZE(0..max-Smach-msgs-SmachContainerStructure)) OF T-String,
        internal-outcomes SEQUENCE (SIZE(0..max-Smach-msgs-SmachContainerStructure)) OF T-String,
        outcomes-from SEQUENCE (SIZE(0..max-Smach-msgs-SmachContainerStructure)) OF T-String,
        outcomes-to SEQUENCE (SIZE(0..max-Smach-msgs-SmachContainerStructure)) OF T-String,
        container-outcomes SEQUENCE (SIZE(0..max-Smach-msgs-SmachContainerStructure)) OF T-String
    }
    -- ================================================================================

END
