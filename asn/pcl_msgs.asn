-- Generated from package.asn.mako for package pcl_msgs

Pcl-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Sensor-msgs-PointCloud2 FROM Sensor-msgs-Types
Std-msgs-Header FROM Std-msgs-Types
max-Pcl-msgs-ModelCoefficients, max-Pcl-msgs-PointIndices, max-Pcl-msgs-PolygonMesh, max-Pcl-msgs-Vertices, Dummy-Pcl-msgs-Types-T FROM UserDefs-Pcl-msgs-Types;
    -- ================================================================================
    -- Message Pcl-msgs-Types/ModelCoefficients
    -- ================================================================================
    -- Header header
    -- float32[] values
    -- 
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Pcl-msgs-Types/ModelCoefficients
    Pcl-msgs-ModelCoefficients ::= SEQUENCE
    {
        header Std-msgs-Header,
        values SEQUENCE (SIZE(0..max-Pcl-msgs-ModelCoefficients)) OF T-Float
    }
    -- ================================================================================

    -- ================================================================================
    -- Message Pcl-msgs-Types/PointIndices
    -- ================================================================================
    -- Header header
    -- int32[] indices
    -- 
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Pcl-msgs-Types/PointIndices
    Pcl-msgs-PointIndices ::= SEQUENCE
    {
        header Std-msgs-Header,
        indices SEQUENCE (SIZE(0..max-Pcl-msgs-PointIndices)) OF T-Int32
    }
    -- ================================================================================

    -- ================================================================================
    -- Message Pcl-msgs-Types/PolygonMesh
    -- ================================================================================
    -- # Separate header for the polygonal surface
    -- Header header
    -- # Vertices of the mesh as a point cloud
    -- sensor_msgs/PointCloud2 cloud
    -- # List of polygons
    -- Vertices[] polygons
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: sensor_msgs/PointCloud2
    -- # This message holds a collection of N-dimensional points, which may
    -- # contain additional information such as normals, intensity, etc. The
    -- # point data is stored as a binary blob, its layout described by the
    -- # contents of the "fields" array.
    -- 
    -- # The point cloud data may be organized 2d (image-like) or 1d
    -- # (unordered). Point clouds organized as 2d images may be produced by
    -- # camera depth sensors such as stereo or time-of-flight.
    -- 
    -- # Time of sensor data acquisition, and the coordinate frame ID (for 3d
    -- # points).
    -- Header header
    -- 
    -- # 2D structure of the point cloud. If the cloud is unordered, height is
    -- # 1 and width is the length of the point cloud.
    -- uint32 height
    -- uint32 width
    -- 
    -- # Describes the channels and their layout in the binary data blob.
    -- PointField[] fields
    -- 
    -- bool    is_bigendian # Is this data bigendian?
    -- uint32  point_step   # Length of a point in bytes
    -- uint32  row_step     # Length of a row in bytes
    -- uint8[] data         # Actual point data, size is (row_step*height)
    -- 
    -- bool is_dense        # True if there are no invalid points
    -- 
    -- ================================================================================
    -- MSG: sensor_msgs/PointField
    -- # This message holds the description of one point entry in the
    -- # PointCloud2 message format.
    -- uint8 INT8    = 1
    -- uint8 UINT8   = 2
    -- uint8 INT16   = 3
    -- uint8 UINT16  = 4
    -- uint8 INT32   = 5
    -- uint8 UINT32  = 6
    -- uint8 FLOAT32 = 7
    -- uint8 FLOAT64 = 8
    -- 
    -- string name      # Name of field
    -- uint32 offset    # Offset from start of point struct
    -- uint8  datatype  # Datatype enumeration, see above
    -- uint32 count     # How many elements in the field
    -- 
    -- ================================================================================
    -- MSG: pcl_msgs/Vertices
    -- # List of point indices
    -- uint32[] vertices
    -- ================================================================================
    -- ASN.1 type for Pcl-msgs-Types/PolygonMesh
    Pcl-msgs-PolygonMesh ::= SEQUENCE
    {
        header Std-msgs-Header,
        cloud Sensor-msgs-PointCloud2,
        polygons SEQUENCE (SIZE(0..max-Pcl-msgs-PolygonMesh)) OF Pcl-msgs-Vertices
    }
    -- ================================================================================

    -- ================================================================================
    -- Message Pcl-msgs-Types/Vertices
    -- ================================================================================
    -- # List of point indices
    -- uint32[] vertices
    -- ================================================================================
    -- ASN.1 type for Pcl-msgs-Types/Vertices
    Pcl-msgs-Vertices ::= SEQUENCE (SIZE(0..max-Pcl-msgs-Vertices)) OF T-UInt32
    -- ================================================================================

END
