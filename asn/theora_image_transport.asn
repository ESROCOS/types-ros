-- Generated from package.asn.mako for package theora_image_transport

Theora-image-transport-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Std-msgs-Header FROM Std-msgs-Types
max-Theora-image-transport-Packet, Dummy-Theora-image-transport-Types-T FROM UserDefs-Theora-image-transport-Types;
    -- ================================================================================
    -- Message Theora-image-transport-Types/Packet
    -- ================================================================================
    -- # ROS message adaptation of the ogg_packet struct from libogg,
    -- # see http://www.xiph.org/ogg/doc/libogg/ogg_packet.html.
    -- 
    -- Header header     # Original sensor_msgs/Image header
    -- uint8[] data      # Raw Theora packet data (combines packet and bytes fields from ogg_packet)
    -- int32 b_o_s       # Flag indicating whether this packet begins a logical bitstream
    -- int32 e_o_s       # Flag indicating whether this packet ends a bitstream
    -- int64 granulepos  # A number indicating the position of this packet in the decoded data
    -- int64 packetno    # Sequential number of this packet in the ogg bitstream
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Theora-image-transport-Types/Packet
    Theora-image-transport-Packet ::= SEQUENCE
    {
        header Std-msgs-Header,
        data-value OCTET STRING (SIZE(0..max-Theora-image-transport-Packet)),
        b-o-s T-Int32,
        e-o-s T-Int32,
        granulepos T-Int64,
        packetno T-Int64
    }
    -- ================================================================================

END
