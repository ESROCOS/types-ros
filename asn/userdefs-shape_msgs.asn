-- Generated from userdefs.asn.mako for package shape_msgs

UserDefs-Shape-msgs-Types DEFINITIONS ::=
BEGIN

IMPORTS T-UInt32 FROM TASTE-BasicTypes;

    -- Dummy type (TASTE doesn't handle the includes correctly if an ASN.1 file defines only constants)
    Dummy-Shape-msgs-Types-T ::= T-UInt32

    -- Size constants definitions: to be set according to the application's needs

    -- Size constant for type Shape-msgs-SolidPrimitive
    max-Shape-msgs-SolidPrimitive T-UInt32 ::= 60

    -- Size constant for type Shape-msgs-Mesh
    max-Shape-msgs-Mesh T-UInt32 ::= 60

END
