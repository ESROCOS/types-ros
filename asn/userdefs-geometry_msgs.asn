-- Generated from userdefs.asn.mako for package geometry_msgs

UserDefs-Geometry-msgs-Types DEFINITIONS ::=
BEGIN

IMPORTS T-UInt32 FROM TASTE-BasicTypes;

    -- Dummy type (TASTE doesn't handle the includes correctly if an ASN.1 file defines only constants)
    Dummy-Geometry-msgs-Types-T ::= T-UInt32

    -- Size constants definitions: to be set according to the application's needs

    -- Size constant for type Geometry-msgs-PoseArray
    max-Geometry-msgs-PoseArray T-UInt32 ::= 60

    -- Size constant for type Geometry-msgs-Polygon
    max-Geometry-msgs-Polygon T-UInt32 ::= 60

END
