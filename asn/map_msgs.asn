-- Generated from package.asn.mako for package map_msgs

Map-msgs-Types DEFINITIONS ::=
BEGIN

IMPORTS
T-Boolean, T-Int8, T-UInt8, T-Int32, T-UInt32 FROM TASTE-BasicTypes
T-Int16, T-UInt16, T-Int64, T-UInt64, T-Float, T-Double, T-String, T-Time FROM TASTE-ExtendedTypes
Nav-msgs-OccupancyGrid FROM Nav-msgs-Types
Sensor-msgs-PointCloud2 FROM Sensor-msgs-Types
Std-msgs-Header FROM Std-msgs-Types
max-Map-msgs-OccupancyGridUpdate, Dummy-Map-msgs-Types-T FROM UserDefs-Map-msgs-Types;
    -- ================================================================================
    -- Message Map-msgs-Types/OccupancyGridUpdate
    -- ================================================================================
    -- Header header
    -- int32 x
    -- int32 y
    -- uint32 width
    -- uint32 height
    -- int8[] data
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- ================================================================================
    -- ASN.1 type for Map-msgs-Types/OccupancyGridUpdate
    Map-msgs-OccupancyGridUpdate ::= SEQUENCE
    {
        header Std-msgs-Header,
        x T-Int32,
        y T-Int32,
        width T-UInt32,
        height T-UInt32,
        data-value SEQUENCE (SIZE(0..max-Map-msgs-OccupancyGridUpdate)) OF T-Int8
    }
    -- ================================================================================

    -- ================================================================================
    -- Message Map-msgs-Types/PointCloud2Update
    -- ================================================================================
    -- uint32 ADD=0
    -- uint32 DELETE=1
    -- Header header
    -- uint32 type          # type of update, one of ADD or DELETE
    -- sensor_msgs/PointCloud2 points
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: sensor_msgs/PointCloud2
    -- # This message holds a collection of N-dimensional points, which may
    -- # contain additional information such as normals, intensity, etc. The
    -- # point data is stored as a binary blob, its layout described by the
    -- # contents of the "fields" array.
    -- 
    -- # The point cloud data may be organized 2d (image-like) or 1d
    -- # (unordered). Point clouds organized as 2d images may be produced by
    -- # camera depth sensors such as stereo or time-of-flight.
    -- 
    -- # Time of sensor data acquisition, and the coordinate frame ID (for 3d
    -- # points).
    -- Header header
    -- 
    -- # 2D structure of the point cloud. If the cloud is unordered, height is
    -- # 1 and width is the length of the point cloud.
    -- uint32 height
    -- uint32 width
    -- 
    -- # Describes the channels and their layout in the binary data blob.
    -- PointField[] fields
    -- 
    -- bool    is_bigendian # Is this data bigendian?
    -- uint32  point_step   # Length of a point in bytes
    -- uint32  row_step     # Length of a row in bytes
    -- uint8[] data         # Actual point data, size is (row_step*height)
    -- 
    -- bool is_dense        # True if there are no invalid points
    -- 
    -- ================================================================================
    -- MSG: sensor_msgs/PointField
    -- # This message holds the description of one point entry in the
    -- # PointCloud2 message format.
    -- uint8 INT8    = 1
    -- uint8 UINT8   = 2
    -- uint8 INT16   = 3
    -- uint8 UINT16  = 4
    -- uint8 INT32   = 5
    -- uint8 UINT32  = 6
    -- uint8 FLOAT32 = 7
    -- uint8 FLOAT64 = 8
    -- 
    -- string name      # Name of field
    -- uint32 offset    # Offset from start of point struct
    -- uint8  datatype  # Datatype enumeration, see above
    -- uint32 count     # How many elements in the field
    -- ================================================================================
    -- ASN.1 type for Map-msgs-Types/PointCloud2Update
    Map-msgs-PointCloud2Update ::= SEQUENCE
    {
        header Std-msgs-Header,
        type-value T-UInt32,
        points Sensor-msgs-PointCloud2
    }
    -- ================================================================================

    -- ================================================================================
    -- Message Map-msgs-Types/ProjectedMap
    -- ================================================================================
    -- nav_msgs/OccupancyGrid map
    -- float64 min_z
    -- float64 max_z
    -- ================================================================================
    -- MSG: nav_msgs/OccupancyGrid
    -- # This represents a 2-D grid map, in which each cell represents the probability of
    -- # occupancy.
    -- 
    -- Header header 
    -- 
    -- #MetaData for the map
    -- MapMetaData info
    -- 
    -- # The map data, in row-major order, starting with (0,0).  Occupancy
    -- # probabilities are in the range [0,100].  Unknown is -1.
    -- int8[] data
    -- 
    -- ================================================================================
    -- MSG: std_msgs/Header
    -- # Standard metadata for higher-level stamped data types.
    -- # This is generally used to communicate timestamped data 
    -- # in a particular coordinate frame.
    -- # 
    -- # sequence ID: consecutively increasing ID 
    -- uint32 seq
    -- #Two-integer timestamp that is expressed as:
    -- # * stamp.sec: seconds (stamp_secs) since epoch (in Python the variable is called 'secs')
    -- # * stamp.nsec: nanoseconds since stamp_secs (in Python the variable is called 'nsecs')
    -- # time-handling sugar is provided by the client library
    -- time stamp
    -- #Frame this data is associated with
    -- # 0: no frame
    -- # 1: global frame
    -- string frame_id
    -- 
    -- ================================================================================
    -- MSG: nav_msgs/MapMetaData
    -- # This hold basic information about the characterists of the OccupancyGrid
    -- 
    -- # The time at which the map was loaded
    -- time map_load_time
    -- # The map resolution [m/cell]
    -- float32 resolution
    -- # Map width [cells]
    -- uint32 width
    -- # Map height [cells]
    -- uint32 height
    -- # The origin of the map [m, m, rad].  This is the real-world pose of the
    -- # cell (0,0) in the map.
    -- geometry_msgs/Pose origin
    -- ================================================================================
    -- MSG: geometry_msgs/Pose
    -- # A representation of pose in free space, composed of position and orientation. 
    -- Point position
    -- Quaternion orientation
    -- 
    -- ================================================================================
    -- MSG: geometry_msgs/Point
    -- # This contains the position of a point in free space
    -- float64 x
    -- float64 y
    -- float64 z
    -- 
    -- ================================================================================
    -- MSG: geometry_msgs/Quaternion
    -- # This represents an orientation in free space in quaternion form.
    -- 
    -- float64 x
    -- float64 y
    -- float64 z
    -- float64 w
    -- ================================================================================
    -- ASN.1 type for Map-msgs-Types/ProjectedMap
    Map-msgs-ProjectedMap ::= SEQUENCE
    {
        map-value Nav-msgs-OccupancyGrid,
        min-z T-Double,
        max-z T-Double
    }
    -- ================================================================================

    -- ================================================================================
    -- Message Map-msgs-Types/ProjectedMapInfo
    -- ================================================================================
    -- string frame_id
    -- float64 x
    -- float64 y
    -- float64 width
    -- float64 height
    -- float64 min_z
    -- float64 max_z    -- ================================================================================
    -- ASN.1 type for Map-msgs-Types/ProjectedMapInfo
    Map-msgs-ProjectedMapInfo ::= SEQUENCE
    {
        frame-id T-String,
        x T-Double,
        y T-Double,
        width T-Double,
        height T-Double,
        min-z T-Double,
        max-z T-Double
    }
    -- ================================================================================

END
