-- Generated from userdefs.asn.mako for package tf

UserDefs-Tf-Types DEFINITIONS ::=
BEGIN

IMPORTS T-UInt32 FROM TASTE-BasicTypes;

    -- Dummy type (TASTE doesn't handle the includes correctly if an ASN.1 file defines only constants)
    Dummy-Tf-Types-T ::= T-UInt32

    -- Size constants definitions: to be set according to the application's needs

    -- Size constant for type Tf-tfMessage
    max-Tf-tfMessage T-UInt32 ::= 60

END
