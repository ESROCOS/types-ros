-- Generated from userdefs.asn.mako for package tf2_msgs

UserDefs-Tf2-msgs-Types DEFINITIONS ::=
BEGIN

IMPORTS T-UInt32 FROM TASTE-BasicTypes;

    -- Dummy type (TASTE doesn't handle the includes correctly if an ASN.1 file defines only constants)
    Dummy-Tf2-msgs-Types-T ::= T-UInt32

    -- Size constants definitions: to be set according to the application's needs

    -- Size constant for type Tf2-msgs-TFMessage
    max-Tf2-msgs-TFMessage T-UInt32 ::= 60

END
